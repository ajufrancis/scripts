-- **************************************************************************
-- HILLSTONE-SERVICEBOOK-MEMBER-MIB 
--
-- Copyright (c) 2009 by Hillstone Networks, Inc.
-- All rights reserved.
-- 
-- Version:      V3   
-- Description:	 Hillstone Networks SERVICEBOOK MEMBER MIB Object Identifier Assignments
-- **************************************************************************
--

HILLSTONE-SERVICEBOOK-MEMBER-MIB DEFINITIONS ::= BEGIN

IMPORTS
	hillstoneServiceBookMember
		FROM HILLSTONE-SMI
	OBJECT-TYPE
		FROM RFC-1212
        RowStatus		
		FROM SNMPv2-TC;

hillstoneServiceBookMemberObjects OBJECT IDENTIFIER ::= { hillstoneServiceBookMember 1 }

hillstoneServiceBookMemberTable OBJECT-TYPE
	SYNTAX SEQUENCE OF hillstoneServiceBookMemberEntry
	MAX-ACCESS not-accessible
	STATUS current
	DESCRIPTION
	    "This table contains all the ServiceBookMember defined in the system."
::= { hillstoneServiceBookMemberObjects 1 }

hillstoneServiceBookMemberEntry OBJECT-TYPE
	SYNTAX hillstoneServiceBookMemberEntry
	MAX-ACCESS not-accessible
	STATUS current
	DESCRIPTION
		"Defined the parameters of ServiceBookMember."
INDEX { hillstoneServiceBookName, hillstoneServiceBookMemberId }
::= { hillstoneServiceBookMemberTable 1 }
	
hillstoneServiceBookMemberEntry ::=
SEQUENCE { 
	hillstoneServiceBookName
		OCTET STRING,
	hillstoneServiceBookMemberId
		INTEGER,
	hillstoneServiceBookMemberProtocol
		INTEGER,
	hillstoneServiceBookMemberDestationMinPort
		INTEGER,
	hillstoneServiceBookMemberDestationMaxPort
		INTEGER,
	hillstoneServiceBookMemberSourceMinPort
		INTEGER,
	hillstoneServiceBookMemberSourceMaxPort
		INTEGER,
	hillstoneServiceBookMemberAppType
		INTEGER,
	hillstoneServiceBookMemberTimeout
		Gauge,
	hillstoneServiceBookMemberRowStatus
		RowStatus
	}

hillstoneServiceBookName OBJECT-TYPE
	SYNTAX OCTET STRING (SIZE (1..31))
	MAX-ACCESS read-write
	STATUS current
	DESCRIPTION
	    "The name of ServiceBook.
	    Different ServiceBook has different name."
::= { hillstoneServiceBookMemberEntry 1 }

hillstoneServiceBookMemberId OBJECT-TYPE
	SYNTAX INTEGER
	MAX-ACCESS read-write
	STATUS current
	DESCRIPTION
	    "The id of ServiceBookMember for one service."
::= { hillstoneServiceBookMemberEntry 2 }

hillstoneServiceBookMemberProtocol OBJECT-TYPE
	SYNTAX INTEGER
	{
		Any(0),
		ICMP(1),
		other(2),
		IP-IP(4),		
		TCP(6),
		UDP(17),
		IP-IPv6(41),
		GRE(47),
		ESP(50),
		AH(51)
	}
	MAX-ACCESS read-write
	STATUS current
	DESCRIPTION
	    "The protocol type of ServiceBookMember."
::= { hillstoneServiceBookMemberEntry 3 }
  
hillstoneServiceBookMemberDestationMinPort OBJECT-TYPE
	SYNTAX	INTEGER
	MAX-ACCESS read-write
	STATUS current
	DESCRIPTION
	    "The destation min port of udp/tcp or the min code of icmp."
::= { hillstoneServiceBookMemberEntry 4 }

hillstoneServiceBookMemberDestationMaxPort OBJECT-TYPE
	SYNTAX	INTEGER
	MAX-ACCESS read-write
	STATUS current
	DESCRIPTION
	    "The destation max port of udp/tcp or the max code of icmp."
::= { hillstoneServiceBookMemberEntry 5 }

hillstoneServiceBookMemberSourceMinPort OBJECT-TYPE
	SYNTAX	INTEGER
	MAX-ACCESS read-write
	STATUS current
	DESCRIPTION
	    "If protocol type is udp/tcp, the value is min source port;
	    if protocol type is icmp, the value is the code type of icmp;
	    if protocol type is other, the value is the protocol number"
::= { hillstoneServiceBookMemberEntry 6 }

hillstoneServiceBookMemberSourceMaxPort OBJECT-TYPE
	SYNTAX	INTEGER
	MAX-ACCESS read-write
	STATUS current
	DESCRIPTION
	    "The source min port of udp/tcp."
::= { hillstoneServiceBookMemberEntry 7 }

hillstoneServiceBookMemberAppType OBJECT-TYPE
	SYNTAX	INTEGER
	{
		none(0),
		ftp(4),
		rsh(20),
		http(10),
		rtsp(19),
		tftp(9),
		msrpc-epm(13),
		sunrpc-bind(12),
		telnet(5),
		sqlnetv1(24),
		sqlnetv2(25),
		realmedia(23),
		userdefined(65535)
	}
	MAX-ACCESS read-write
	STATUS current
	DESCRIPTION
	    "The application type of a service row"
::= { hillstoneServiceBookMemberEntry 8 }

hillstoneServiceBookMemberTimeout OBJECT-TYPE
	SYNTAX	Gauge
	MAX-ACCESS read-write
	STATUS current
	DESCRIPTION
	    "The timeout of a service row."
::= { hillstoneServiceBookMemberEntry 9 }	

hillstoneServiceBookMemberRowStatus OBJECT-TYPE
	SYNTAX RowStatus
	MAX-ACCESS read-create
	STATUS current
	DESCRIPTION
	 "The status of this service book row. support: active, createandgo, destory"
::= { hillstoneServiceBookMemberEntry 10 }

END
