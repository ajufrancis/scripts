-- **************************************************************************
-- HILLSTONE-POLICY-SOURCE-ADDRESS-MIB 
--
-- Copyright (c) 2009 by Hillstone Networks, Inc.
-- All rights reserved.
-- 
-- Version:      V3   
-- Description:	 Hillstone Networks policy source address MIB Object Identifier Assignments
-- **************************************************************************
--

HILLSTONE-POLICY-SOURCE-ADDRESS-MIB DEFINITIONS ::= BEGIN

IMPORTS
	hillstonePolicySourceAddress
		FROM HILLSTONE-SMI
	OBJECT-TYPE
		FROM RFC-1212	
        RowStatus		
		FROM SNMPv2-TC;

hillstonePolicySourceAddressObjects OBJECT IDENTIFIER ::= { hillstonePolicySourceAddress 1 }

hillstonePolicySourceAddressTable OBJECT-TYPE
	SYNTAX SEQUENCE OF hillstonePolicySourceAddressEntry
	MAX-ACCESS not-accessible
	STATUS current
	DESCRIPTION
	    "This table contains all the PolicySourceAddress defined in the system."
::= { hillstonePolicySourceAddressObjects 1 }

hillstonePolicySourceAddressEntry OBJECT-TYPE
	SYNTAX hillstonePolicySourceAddressEntry
	MAX-ACCESS not-accessible
	STATUS current
	DESCRIPTION
		"Define the parameters of PolicySourceAddress."
INDEX { hillstonePolicyId, hillstonePolicySourceAddressSrcAddrId }
::= { hillstonePolicySourceAddressTable 1 }
	
hillstonePolicySourceAddressEntry ::=
SEQUENCE { 
	hillstonePolicyId
		INTEGER,
	hillstonePolicySourceAddressType
		INTEGER,
	hillstoneAddressBookName
		OCTET STRING,
	hillstonePolicySourceAddressSrcIP
		IpAddress,
	hillstonePolicySourceAddressSrcIPMask
		IpAddress,
	hillstonePolicySourceAddressSrcAddrId
		INTEGER,
	hillstonePolicySourceAddressSrcHost
		OCTET STRING,
	hillstonePolicySourceAddressSrcRangeMinIpAddr
		IpAddress,
	hillstonePolicySourceAddressSrcRangeMaxIpAddr
		IpAddress,
  hillstonePolicySourceAddressRowStatus
		RowStatus
	}

hillstonePolicyId OBJECT-TYPE
	SYNTAX INTEGER 
	ACCESS read-only
	STATUS current
	DESCRIPTION
	    "The id of Policy table."
::= { hillstonePolicySourceAddressEntry 1 }

hillstonePolicySourceAddressType OBJECT-TYPE
	SYNTAX INTEGER 
	{
		src-addr(0),
		src-ip(1),
		src-host(2),
		src-range(3)
	}
	ACCESS  read-write
	STATUS current
	DESCRIPTION
	    "
	    The source address type of policy.
	    "
::= { hillstonePolicySourceAddressEntry 2 }

hillstoneAddressBookName OBJECT-TYPE
	SYNTAX OCTET STRING (SIZE (1..31))
	MAX-ACCESS read-write
	STATUS current
	DESCRIPTION
	    "The name of address book"
::= { hillstonePolicySourceAddressEntry 3 }
  
hillstonePolicySourceAddressSrcIP OBJECT-TYPE
	SYNTAX IpAddress
	MAX-ACCESS  read-write
	STATUS current
	DESCRIPTION
	    "The ip address of source address"
::= { hillstonePolicySourceAddressEntry 4 }

hillstonePolicySourceAddressSrcIPMask OBJECT-TYPE
	SYNTAX IpAddress
	MAX-ACCESS  read-write
	STATUS current
	DESCRIPTION
	    "The ip mask of source address"
::= { hillstonePolicySourceAddressEntry 5 }
 
hillstonePolicySourceAddressSrcAddrId OBJECT-TYPE
	SYNTAX INTEGER
	MAX-ACCESS  read-write
	STATUS current
	DESCRIPTION
	    "The id of addressbook"
::= { hillstonePolicySourceAddressEntry 6 }

hillstonePolicySourceAddressSrcHost OBJECT-TYPE
	SYNTAX OCTET STRING (SIZE (1..31))
	MAX-ACCESS  read-write
	STATUS current
	DESCRIPTION
	    "The hostname of source address"
::= { hillstonePolicySourceAddressEntry 7 }

hillstonePolicySourceAddressSrcRangeMinIpAddr OBJECT-TYPE
	SYNTAX IpAddress
	MAX-ACCESS  read-write
	STATUS current
	DESCRIPTION
	    "The min ip of source address"
::= { hillstonePolicySourceAddressEntry 8 }

hillstonePolicySourceAddressSrcRangeMaxIpAddr OBJECT-TYPE
	SYNTAX IpAddress
	MAX-ACCESS  read-write
	STATUS current
	DESCRIPTION
	    "The max ip of source address"
::= { hillstonePolicySourceAddressEntry 9 }

hillstonePolicySourceAddressRowStatus OBJECT-TYPE
	SYNTAX RowStatus
	MAX-ACCESS read-create
	STATUS current
	DESCRIPTION
	 "The status of this PolicySourceAddress row."
::= { hillstonePolicySourceAddressEntry 10 }

END
