-- **************************************************************************
-- HILLSTONE-ADDRESSBOOK-MEMBER-MIB 
--
-- Copyright (c) 2009 by Hillstone Networks, Inc.
-- All rights reserved.
-- 
-- Version:      V3   
-- Description:	 Hillstone Networks Address Book MIB Object Identifier Assignments
-- **************************************************************************
--

HILLSTONE-ADDRESSBOOK-MEMBER-MIB DEFINITIONS ::= BEGIN

IMPORTS
	hillstoneAddressBookMember
		FROM HILLSTONE-SMI
	OBJECT-TYPE
		FROM RFC-1212	
	RowStatus		
		FROM SNMPv2-TC;

hillstoneAddrMemberObjects OBJECT IDENTIFIER ::= { hillstoneAddressBookMember 1 }

hillstoneAddrMemberTable OBJECT-TYPE
	SYNTAX SEQUENCE OF hillstoneAddrMemberEntry
	MAX-ACCESS not-accessible
	STATUS current
	DESCRIPTION
	    "This table contains all the AddressBookMember defined in the system."
::= { hillstoneAddrMemberObjects 1 }

hillstoneAddrMemberEntry OBJECT-TYPE
	SYNTAX hillstoneAddrMemberEntry
	MAX-ACCESS not-accessible
	STATUS current
	DESCRIPTION
		"Defined the parameters of AddressBookMember."
INDEX { hillstoneAddrName, hillstoneAddrMemberId }

::= { hillstoneAddrMemberTable 1 }
	
hillstoneAddrMemberEntry ::=
SEQUENCE { 	
	hillstoneAddrName
		OCTET STRING,
	hillstoneAddrMemberId
		INTEGER,
	hillstoneAddrMemberType
		INTEGER,
	hillstoneAddrMemberIp
		IpAddress,
	hillstoneAddrMemberIpMask
		IpAddress,
	hillstoneAddrMemberIpRangeMin
		IpAddress,
	hillstoneAddrMemberIpRangeMax
		IpAddress,
	hillstoneAddrMemberHostName
		OCTET STRING,
	hillstoneAddrMemberName
		OCTET STRING,
	hillstoneAddrMemberRowStatus
		RowStatus
	}

hillstoneAddrName OBJECT-TYPE
	SYNTAX OCTET STRING (SIZE (1..31))
	MAX-ACCESS read-write
	STATUS current
	DESCRIPTION
	    "The name of address book"
::= { hillstoneAddrMemberEntry 1 }

hillstoneAddrMemberId OBJECT-TYPE
	SYNTAX INTEGER 
	MAX-ACCESS read-only
	STATUS current
	DESCRIPTION
	    "An internal number to distinguish AddressBook.
	    Different AddressBook has different number."
::= { hillstoneAddrMemberEntry 2 }

hillstoneAddrMemberType OBJECT-TYPE
	SYNTAX INTEGER
	{
		member(0),
		ip(1),
		host(2),
		ip-range(3)
	}
	MAX-ACCESS read-write
	STATUS current
	DESCRIPTION
	    "The member type of address book."
::= { hillstoneAddrMemberEntry 3 }

hillstoneAddrMemberIp OBJECT-TYPE
	SYNTAX IpAddress 
	MAX-ACCESS read-write
	STATUS current
	DESCRIPTION
	    "An ipaddress of member-ip"
::= { hillstoneAddrMemberEntry 4 }

hillstoneAddrMemberIpMask OBJECT-TYPE
	SYNTAX IpAddress 
	MAX-ACCESS read-write
	STATUS current
	DESCRIPTION
	    "Ipmask of member-ip"
::= { hillstoneAddrMemberEntry 5 }

hillstoneAddrMemberIpRangeMin OBJECT-TYPE
	SYNTAX IpAddress 
	MAX-ACCESS read-write
	STATUS current
	DESCRIPTION
	    "The min ip of member-iprange"
::= { hillstoneAddrMemberEntry 6 }

hillstoneAddrMemberIpRangeMax OBJECT-TYPE
	SYNTAX IpAddress 
	MAX-ACCESS read-write
	STATUS current
	DESCRIPTION
	    "The max ip of member-iprange"
::= { hillstoneAddrMemberEntry 7 }

hillstoneAddrMemberHostName OBJECT-TYPE
	SYNTAX OCTET STRING (SIZE (1..63))
	MAX-ACCESS read-write
	STATUS current
	DESCRIPTION
	    "A hostname of member"
::= { hillstoneAddrMemberEntry 8 }

hillstoneAddrMemberName OBJECT-TYPE
	SYNTAX OCTET STRING (SIZE (1..31))
	MAX-ACCESS read-write
	STATUS current
	DESCRIPTION
	    "The sub member name"
::= { hillstoneAddrMemberEntry 9 }

hillstoneAddrMemberRowStatus OBJECT-TYPE
	SYNTAX RowStatus
	MAX-ACCESS read-create
	STATUS current
	DESCRIPTION
	 "The status of this address book member row. support: active, createandgo, destory"
::= { hillstoneAddrMemberEntry 10 }

END
