-- **************************************************************************
-- HILLSTONE-POLICY-MOVEMENT-MIB
--
-- Copyright (c) 2009 by Hillstone Networks, Inc.
-- All rights reserved.
-- 
-- Version:      V3   
-- Description:	 Hillstone Networks POLICY MOVEMENT MIB Object Identifier Assignments
-- **************************************************************************
--

HILLSTONE-POLICY-MOVEMENT-MIB DEFINITIONS ::= BEGIN

IMPORTS
	hillstonePolicyMovement
		FROM HILLSTONE-SMI
	OBJECT-TYPE
		FROM RFC-1212	
        RowStatus		
		FROM SNMPv2-TC;

          -- textual conventions

          DisplayString ::=
              OCTET STRING
          -- This data type is used to model textual information taken
          -- from the NVT ASCII character set.  By convention, objects
          -- with this syntax are declared as having
          --
          --      SIZE (0..255)

hillstonePolicyMovementObjects OBJECT IDENTIFIER ::= { hillstonePolicyMovement 1 }

hillstonePolicyMovementTable OBJECT-TYPE
	SYNTAX SEQUENCE OF hillstonePolicyMovementEntry
	MAX-ACCESS not-accessible
	STATUS current
	DESCRIPTION
	    "This table contains all the policy movement data."
::= { hillstonePolicyMovementObjects 1 }

hillstonePolicyMovementEntry OBJECT-TYPE
	SYNTAX hillstonePolicyMovementEntry
	MAX-ACCESS not-accessible
	STATUS current
	DESCRIPTION
		"Define the parameters of policy movement."
INDEX { hillstonePolicyId }
::= { hillstonePolicyMovementTable 1 }
	
hillstonePolicyMovementEntry ::=
SEQUENCE { 
	hillstonePolicyId
		INTEGER,
	hillstonePolicyMoveAction
		INTEGER,
	hillstonePolicyDstPosition
		INTEGER,
  hillstonePolicyMovementRowStatus
		RowStatus
	}

hillstonePolicyId OBJECT-TYPE
	SYNTAX INTEGER 
	ACCESS read-only
	STATUS current
	DESCRIPTION
	    "The id of policy, which will be moved."
::= { hillstonePolicyMovementEntry 1 }

hillstonePolicyMoveAction OBJECT-TYPE
	SYNTAX INTEGER
	{
		after(1),
		before(2),
		bottom(3),		
		top(4)
	}
	ACCESS  read-write
	STATUS current
	DESCRIPTION
	    "The move action type."
::= { hillstonePolicyMovementEntry 2 }
  
hillstonePolicyDstPosition OBJECT-TYPE
	SYNTAX INTEGER
	ACCESS  read-write
	STATUS current
	DESCRIPTION
	    "
	    The destination position of policy.
	    "
::= { hillstonePolicyMovementEntry 3 }

hillstonePolicyMovementRowStatus OBJECT-TYPE
	SYNTAX RowStatus
	MAX-ACCESS read-create
	STATUS current
	DESCRIPTION
	 "The status of this policy movement row."
::= { hillstonePolicyMovementEntry 4 }

END
