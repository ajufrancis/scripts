-- **************************************************************************
-- HILLSTONE-POLICY-SCHEDULE-MEMBER-MIB 
--
-- Copyright (c) 2009 by Hillstone Networks, Inc.
-- All rights reserved.
-- 
-- Version:      V3   
-- Description:	 Hillstone Networks Policy Schedule MIB Object Identifier Assignments
-- **************************************************************************
--

HILLSTONE-POLICY-SCHEDULE-MIB DEFINITIONS ::= BEGIN

IMPORTS
	hillstonePolicySchedule
		FROM HILLSTONE-SMI
	OBJECT-TYPE
		FROM RFC-1212	
	RowStatus		
		FROM SNMPv2-TC;

hillstonePolicyScheduleObjects OBJECT IDENTIFIER ::= { hillstonePolicySchedule 1 }

hillstonePolicyScheduleTable OBJECT-TYPE
	SYNTAX SEQUENCE OF hillstonePolicyScheduleEntry
	MAX-ACCESS not-accessible
	STATUS current
	DESCRIPTION
	    "This table contains all the ServiceGroupMember defined in the system."
::= { hillstonePolicyScheduleObjects 1 }

hillstonePolicyScheduleEntry OBJECT-TYPE
	SYNTAX hillstonePolicyScheduleEntry
	MAX-ACCESS not-accessible
	STATUS current
	DESCRIPTION
		"Defined the parameters of ServiceGroupMember."
INDEX { hillstonePolicyId, hillstonePolicyScheduleName }
::= { hillstonePolicyScheduleTable 1 }
	
hillstonePolicyScheduleEntry ::=
SEQUENCE { 
	hillstonePolicyId
		INTEGER,
	hillstonePolicyScheduleName
		OCTET STRING,
	hillstonePolicyScheduleRowStatus
		RowStatus
	}

hillstonePolicyId OBJECT-TYPE
	SYNTAX INTEGER 
	MAX-ACCESS read-only
	STATUS current
	DESCRIPTION
	    "A policy id of policy tablbe"
::= { hillstonePolicyScheduleEntry 1 }

hillstonePolicyScheduleName OBJECT-TYPE
	SYNTAX OCTET STRING (SIZE (1..31))
	MAX-ACCESS read-write
	STATUS current
	DESCRIPTION
	    "The schedule id of this rule"
::= { hillstonePolicyScheduleEntry 2 }

hillstonePolicyScheduleRowStatus OBJECT-TYPE
	SYNTAX RowStatus
	MAX-ACCESS read-create
	STATUS current
	DESCRIPTION
	 "The status of this service group row. support: active, createandgo, destory"
::= { hillstonePolicyScheduleEntry 3 }

END
