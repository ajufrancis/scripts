-- **************************************************************************
-- HILLSTONE-SERVICEBOOK-MIB 
--
-- Copyright (c) 2009 by Hillstone Networks, Inc.
-- All rights reserved.
-- 
-- Version:      V3   
-- Description:	 Hillstone Networks SERVICEBOOK MIB Object Identifier Assignments
-- **************************************************************************
--

HILLSTONE-SERVICEBOOK-MIB DEFINITIONS ::= BEGIN

IMPORTS
	hillstoneServiceBook
		FROM HILLSTONE-SMI
	OBJECT-TYPE
		FROM RFC-1212
        RowStatus		
		FROM SNMPv2-TC;

hillstoneServiceBookObjects OBJECT IDENTIFIER ::= { hillstoneServiceBook 1 }

hillstoneServiceBookTable OBJECT-TYPE
	SYNTAX SEQUENCE OF hillstoneServiceBookEntry
	MAX-ACCESS not-accessible
	STATUS current
	DESCRIPTION
	    "This table contains all the ServiceBook defined in the system."
::= { hillstoneServiceBookObjects 1 }

hillstoneServiceBookEntry OBJECT-TYPE
	SYNTAX hillstoneServiceBookEntry
	MAX-ACCESS not-accessible
	STATUS current
	DESCRIPTION
		"Defined the parameters of ServiceBook."
INDEX { hillstoneServiceBookName }
::= { hillstoneServiceBookTable 1 }
	
hillstoneServiceBookEntry ::=
SEQUENCE { 
	hillstoneServiceBookName
		OCTET STRING,
	hillstoneServiceBookIsUserdef
		INTEGER,
	hillstoneServiceBookDescription
		OCTET STRING,
	hillstoneServiceBookRowStatus
		RowStatus
	}

hillstoneServiceBookName OBJECT-TYPE
	SYNTAX OCTET STRING (SIZE (1..31))
	MAX-ACCESS read-write
	STATUS current
	DESCRIPTION
	    "The name of ServiceBook.
	    Different ServiceBook has different name."
::= { hillstoneServiceBookEntry 1 }

hillstoneServiceBookIsUserdef OBJECT-TYPE
	SYNTAX INTEGER
	{
		predefined(1),
		userdefined(2)
	}
	MAX-ACCESS read-only
	STATUS current
	DESCRIPTION
	    "The attribute of ServiceBook.
	    Userdefined or Predefined."
::= { hillstoneServiceBookEntry 2 }

hillstoneServiceBookDescription OBJECT-TYPE
	SYNTAX OCTET STRING (SIZE (1..255))
	MAX-ACCESS read-write
	STATUS current
	DESCRIPTION
	    "The description of ServiceBook."
::= { hillstoneServiceBookEntry 3 }

hillstoneServiceBookRowStatus OBJECT-TYPE
	SYNTAX RowStatus
	MAX-ACCESS read-create
	STATUS current
	DESCRIPTION
	 "The status of this service book row. support: active, createandgo, destory"
::= { hillstoneServiceBookEntry 4 }

END
