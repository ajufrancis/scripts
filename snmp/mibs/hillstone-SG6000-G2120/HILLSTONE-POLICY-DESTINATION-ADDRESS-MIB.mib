-- **************************************************************************
-- HILLSTONE-POLICY-DESTINATION-ADDRESS-MIB 
--
-- Copyright (c) 2009 by Hillstone Networks, Inc.
-- All rights reserved.
-- 
-- Version:      V3   
-- Description:	 Hillstone Networks policy destination address MIB Object Identifier Assignments
-- **************************************************************************
--

HILLSTONE-POLICY-DESTINATION-ADDRESS-MIB DEFINITIONS ::= BEGIN

IMPORTS
	hillstonePolicyDestinationAddress
		FROM HILLSTONE-SMI
	OBJECT-TYPE
		FROM RFC-1212	
        RowStatus		
		FROM SNMPv2-TC;

hillstonePolicyDestinationAddressObjects OBJECT IDENTIFIER ::= { hillstonePolicyDestinationAddress 1 }

hillstonePolicyDestinationAddressTable OBJECT-TYPE
	SYNTAX SEQUENCE OF hillstonePolicyDestinationAddressEntry
	MAX-ACCESS not-accessible
	STATUS current
	DESCRIPTION
	    "This table contains all the PolicyDestinationAddress defined in the system."
::= { hillstonePolicyDestinationAddressObjects 1 }

hillstonePolicyDestinationAddressEntry OBJECT-TYPE
	SYNTAX hillstonePolicyDestinationAddressEntry
	MAX-ACCESS not-accessible
	STATUS current
	DESCRIPTION
		"Define the parameters of PolicyDestinationAddress."
INDEX { hillstonePolicyId, hillstonePolicyDestinationAddressSrcAddrId }
::= { hillstonePolicyDestinationAddressTable 1 }
	
hillstonePolicyDestinationAddressEntry ::=
SEQUENCE { 
	hillstonePolicyId
		INTEGER,
	hillstonePolicyDestinationAddressType
		INTEGER,
	hillstoneAddressBookName
		OCTET STRING,
	hillstonePolicyDestinationAddressSrcIP
		IpAddress,
	hillstonePolicyDestinationAddressSrcIPMask
		IpAddress,
	hillstonePolicyDestinationAddressSrcAddrId
		INTEGER,
	hillstonePolicyDestinationAddressSrcHost
		OCTET STRING,
	hillstonePolicyDestinationAddressSrcRangeMinIpAddr
		IpAddress,
	hillstonePolicyDestinationAddressSrcRangeMaxIpAddr
		IpAddress,
  hillstonePolicyDestinationAddressRowStatus
		RowStatus
	}

hillstonePolicyId OBJECT-TYPE
	SYNTAX INTEGER 
	MAX-ACCESS read-only
	STATUS current
	DESCRIPTION
	    "The id of Policy table."
::= { hillstonePolicyDestinationAddressEntry 1 }

hillstonePolicyDestinationAddressType OBJECT-TYPE
	SYNTAX INTEGER 
	{
		dst-addr(0),
		dst-ip(1),
		dst-host(2),
		dst-range(3)
	}
	MAX-ACCESS read-write
	STATUS current
	DESCRIPTION
	    "The Destination address type of policy."
::= { hillstonePolicyDestinationAddressEntry 2 }

hillstoneAddressBookName OBJECT-TYPE
	SYNTAX OCTET STRING (SIZE (1..31))
	MAX-ACCESS read-write
	STATUS current
	DESCRIPTION
	    "The name of address book"
::= { hillstonePolicyDestinationAddressEntry 3 }
  
hillstonePolicyDestinationAddressSrcIP OBJECT-TYPE
	SYNTAX IpAddress
	MAX-ACCESS  read-write
	STATUS current
	DESCRIPTION
	    "The ip address of Destination address"
::= { hillstonePolicyDestinationAddressEntry 4 }

hillstonePolicyDestinationAddressSrcIPMask OBJECT-TYPE
	SYNTAX IpAddress
	MAX-ACCESS  read-write
	STATUS current
	DESCRIPTION
	    "The ip mask of Destination address"
::= { hillstonePolicyDestinationAddressEntry 5 }
 
hillstonePolicyDestinationAddressSrcAddrId OBJECT-TYPE
	SYNTAX INTEGER
	MAX-ACCESS  read-write
	STATUS current
	DESCRIPTION
	    "The id of addressbook"
::= { hillstonePolicyDestinationAddressEntry 6 }

hillstonePolicyDestinationAddressSrcHost OBJECT-TYPE
	SYNTAX OCTET STRING (SIZE (1..31))
	MAX-ACCESS  read-write
	STATUS current
	DESCRIPTION
	    "The hostname of Destination address"
::= { hillstonePolicyDestinationAddressEntry 7 }

hillstonePolicyDestinationAddressSrcRangeMinIpAddr OBJECT-TYPE
	SYNTAX IpAddress
	MAX-ACCESS  read-write
	STATUS current
	DESCRIPTION
	    "The min ip of Destination address"
::= { hillstonePolicyDestinationAddressEntry 8 }

hillstonePolicyDestinationAddressSrcRangeMaxIpAddr OBJECT-TYPE
	SYNTAX IpAddress
	MAX-ACCESS  read-write
	STATUS current
	DESCRIPTION
	    "The max ip of Destination address"
::= { hillstonePolicyDestinationAddressEntry 9 }

hillstonePolicyDestinationAddressRowStatus OBJECT-TYPE
	SYNTAX RowStatus
	MAX-ACCESS read-create
	STATUS current
	DESCRIPTION
	 "The status of this PolicyDestinationAddress row."
::= { hillstonePolicyDestinationAddressEntry 10 }

END
