-- **************************************************************************
-- HILLSTONE-POLICY-MIB 
--
-- Copyright (c) 2009 by Hillstone Networks, Inc.
-- All rights reserved.
-- 
-- Version:      V3   
-- Description:	 Hillstone Networks POLICY MIB Object Identifier Assignments
-- **************************************************************************
--

HILLSTONE-POLICY-MIB DEFINITIONS ::= BEGIN

IMPORTS
	hillstonePolicy
		FROM HILLSTONE-SMI
	OBJECT-TYPE
		FROM RFC-1212	
        RowStatus		
		FROM SNMPv2-TC;

          -- textual conventions

          DisplayString ::=
              OCTET STRING
          -- This data type is used to model textual information taken
          -- from the NVT ASCII character set.  By convention, objects
          -- with this syntax are declared as having
          --
          --      SIZE (0..255)

hillstonePolicyObjects OBJECT IDENTIFIER ::= { hillstonePolicy 1 }

hillstonePolicyDefaultAction OBJECT-TYPE
      SYNTAX  INTEGER 	
      {
	    DENY(0),
	    PERMIT(1)
      }
      ACCESS  read-write
      STATUS  current
      DESCRIPTION
	      "The policy default action"
      ::= { hillstonePolicyObjects 1 }

hillstonePolicyLog OBJECT-TYPE
      SYNTAX INTEGER 	
      {
	    OFF(0),
	    ON(1)
      }
      ACCESS  read-write
      STATUS  current
      DESCRIPTION
	      "Log policy default traffic"
      ::= { hillstonePolicyObjects 2 }

hillstonePolicyTable OBJECT-TYPE
	SYNTAX SEQUENCE OF hillstonePolicyEntry
	MAX-ACCESS not-accessible
	STATUS current
	DESCRIPTION
	    "This table contains all the policy defined in the system."
::= { hillstonePolicyObjects 3 }

hillstonePolicyEntry OBJECT-TYPE
	SYNTAX hillstonePolicyEntry
	MAX-ACCESS not-accessible
	STATUS current
	DESCRIPTION
		"Define the parameters of policy."
INDEX { hillstonePolicySequence, hillstonePolicyId }
::= { hillstonePolicyTable 1 }
	
hillstonePolicyEntry ::=
SEQUENCE { 
	hillstonePolicyId
		INTEGER,
	hillstonePolicySrcZoneId
		INTEGER,
	hillstonePolicyDstZoneId
		INTEGER,
	hillstonePolicyAction
		INTEGER,
	hillstonePolicyLogPolicyDeny
		INTEGER,
	hillstonePolicyLogSessionStart
		INTEGER,
	hillstonePolicyLogSessionEnd
		INTEGER,
	hillstonePolicySequence
		INTEGER,
	hillstonePolicyEnabled
		INTEGER,
  hillstonePolicyRowStatus
		RowStatus
	}

hillstonePolicyId OBJECT-TYPE
	SYNTAX INTEGER 
	ACCESS read-only
	STATUS current
	DESCRIPTION
	    "The id of policy. Different policy has different id."
::= { hillstonePolicyEntry 1 }

hillstonePolicySrcZoneId OBJECT-TYPE
	SYNTAX INTEGER
	ACCESS  read-write
	STATUS current
	DESCRIPTION
	    "
	    The source security zone id of policy.
	    "
::= { hillstonePolicyEntry 2 }
  
hillstonePolicyDstZoneId OBJECT-TYPE
	SYNTAX INTEGER
	ACCESS  read-write
	STATUS current
	DESCRIPTION
	    "
	    The destination security zone id of policy.
	    "
::= { hillstonePolicyEntry 3 }

hillstonePolicyAction OBJECT-TYPE
	SYNTAX INTEGER
	{
		notset(0),
		deny(1),
		permit(2),
		tunnel(3),
		outtunnel(4),
		webauth(5)
	}
	ACCESS  read-write
	STATUS current
	DESCRIPTION
	    "The action of policy"
::= { hillstonePolicyEntry 4 }
	
hillstonePolicyLogPolicyDeny OBJECT-TYPE
	SYNTAX INTEGER 	
  {
	  OFF(0),
	  ON(1)
  }
	ACCESS  read-write
	STATUS current
	DESCRIPTION
	    "Log when policy do deny action"
::= { hillstonePolicyEntry 5 }
 
hillstonePolicyLogSessionStart OBJECT-TYPE
	SYNTAX INTEGER 	
  {
	  OFF(0),
	  ON(1)
  }
	ACCESS  read-write
	STATUS current
	DESCRIPTION
	    "Log when policy session start"
::= { hillstonePolicyEntry 6 }

hillstonePolicyLogSessionEnd OBJECT-TYPE
	SYNTAX INTEGER 	
  {
	  OFF(0),
	  ON(1)
  }
	ACCESS  read-write
	STATUS current
	DESCRIPTION
	    "Log when policy session end"
::= { hillstonePolicyEntry 7 }

hillstonePolicySequence OBJECT-TYPE
	SYNTAX INTEGER
	ACCESS  read-only
	STATUS current
	DESCRIPTION
	    "The sequence of the policy, that represents policy 's priority"
::= { hillstonePolicyEntry 8 }

hillstonePolicyEnabled OBJECT-TYPE
	SYNTAX INTEGER 	
  {
	  Disable(0),
	  Enable(1)
  }
	ACCESS  read-write
	STATUS current
	DESCRIPTION
	    "The enable status of policy"
::= { hillstonePolicyEntry 9 }

hillstonePolicyRowStatus OBJECT-TYPE
	SYNTAX RowStatus
	MAX-ACCESS read-create
	STATUS current
	DESCRIPTION
	 "The status of this policy row."
::= { hillstonePolicyEntry 10 }

END
