ALCATEL-IND1-AAA-MIB DEFINITIONS ::= BEGIN

    IMPORTS
        MODULE-IDENTITY, OBJECT-IDENTITY, OBJECT-TYPE, IpAddress,
        Integer32, Unsigned32, NOTIFICATION-TYPE
            FROM SNMPv2-SMI
        MacAddress, RowStatus
            FROM SNMPv2-TC
        MODULE-COMPLIANCE, OBJECT-GROUP, NOTIFICATION-GROUP
            FROM SNMPv2-CONF
        SnmpAdminString        FROM SNMP-FRAMEWORK-MIB
        InetAddressType, InetAddress
            FROM INET-ADDRESS-MIB
        softentIND1AAA
            FROM ALCATEL-IND1-BASE;


    alcatelIND1AAAMIB MODULE-IDENTITY
        LAST-UPDATED  "201005130000Z"
        ORGANIZATION  "Alcatel-Lucent"
        CONTACT-INFO
            "Please consult with Customer Service to ensure the most appropriate
             version of this document is used with the products in question:

                      Alcatel-Lucent, Enterprise Solutions Division
                    (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"

        DESCRIPTION
            "This module describes an authoritative enterprise-specific Simple
             Network Management Protocol (SNMP) Management Information Base (MIB):

                 For the Birds Of Prey Product Line
                 Authentication, Authorization, and Accounting (AAA) Subsystem.

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

        REVISION      "201005130000Z"
        DESCRIPTION
            "Fixed the Notifications to use MIB Module OID.0 as Notifications root."

        REVISION      "200704030000Z"
        DESCRIPTION
            "The latest version of this MIB Module."

        ::= { softentIND1AAA 1 }



    alcatelIND1AAAMIBObjects OBJECT-IDENTITY
        STATUS current
        DESCRIPTION
            "Branch For Authentication, Authorization, and Accounting (AAA)
            Subsystem Managed Objects."
        ::= { alcatelIND1AAAMIB 1 }


    alcatelIND1AAAMIBConformance OBJECT-IDENTITY
        STATUS current
        DESCRIPTION
            "Branch For Authentication, Authorization, and Accounting (AAA)
            Subsystem Conformance Information."
        ::= { alcatelIND1AAAMIB 2 }


    alcatelIND1AAAMIBGroups OBJECT-IDENTITY
        STATUS current
        DESCRIPTION
            "Branch For Authentication, Authorization, and Accounting (AAA)
            Subsystem Units Of Conformance."
        ::= { alcatelIND1AAAMIBConformance 1 }


    alcatelIND1AAAMIBCompliances OBJECT-IDENTITY
        STATUS current
        DESCRIPTION
            "Branch For Authentication, Authorization, and Accounting (AAA)
            Subsystem Compliance Statements."
        ::= { alcatelIND1AAAMIBConformance 2 }



--    Overview of the AAA MIB
--
--    this MIB provides configuration of the AAA services including the
--    servers and the local user database
--

--    AAA server MIB

    aaaServerMIB    OBJECT IDENTIFIER ::= { alcatelIND1AAAMIBObjects 1 }

--
--    Server configuration table
--

    aaaServerTable OBJECT-TYPE
        SYNTAX        SEQUENCE OF AaaServerEntry
        MAX-ACCESS    not-accessible
        STATUS        current
        DESCRIPTION
            "This table shows current configuration for each AAA server."
        ::= { aaaServerMIB 1 }

    aaaServerEntry OBJECT-TYPE
        SYNTAX        AaaServerEntry
        MAX-ACCESS    not-accessible
        STATUS        current
        DESCRIPTION
            "An AAA server configuration identified by its protocol
             and its index. An entry is created/removed when a server
             is defined or undefined with IOS configuration commands
             via CLI or by issuing appropriate sets to this table
             using snmp."
        INDEX     { aaasName }
        ::= { aaaServerTable 1 }

    AaaServerEntry ::= SEQUENCE
        {
            aaasName            SnmpAdminString,
            aaasProtocol        INTEGER,
            aaasHostName        SnmpAdminString,
            aaasIpAddress       IpAddress,
            aaasHostName2       SnmpAdminString,
            aaasIpAddress2      IpAddress,
            aaasRetries         Integer32,
            aaasTimout          Integer32,
            aaasRadKey          SnmpAdminString,
            aaasRadAuthPort     Integer32,
            aaasRadAcctPort     Integer32,
            aaasLdapPort        Integer32,
            aaasLdapDn          SnmpAdminString,
            aaasLdapPasswd      SnmpAdminString,
            aaasLdapSearchBase  SnmpAdminString,
            aaasLdapServType    INTEGER,
            aaasLdapEnableSsl   INTEGER,
            aaasRowStatus       RowStatus,
            aaasTacacsKey       SnmpAdminString,
            aaasTacacsPort      Integer32,
            aaasVrfName            SnmpAdminString
        }

    aaasName OBJECT-TYPE
        SYNTAX        SnmpAdminString ( SIZE( 0 .. 32 ) )
        MAX-ACCESS    not-accessible
        STATUS        current
        DESCRIPTION
            "Name of the server.
            This name is given by the operator to refer the server."
        ::= { aaaServerEntry 1}

    aaasProtocol OBJECT-TYPE
        SYNTAX        INTEGER
                      {
                          radius(1),
                            ldap(2),
                             ace(3),
                          tacacs(4)
                      }
        MAX-ACCESS    read-create
        STATUS        current
        DESCRIPTION
            "Protocol used with the server:
                 radius(1) - RADIUS
                   ldap(2) - LDAP
                    ace(3) - ACE
                 tacacs(4) - TACACS+"
        ::= { aaaServerEntry 2}

    aaasHostName OBJECT-TYPE
        SYNTAX        SnmpAdminString ( SIZE( 0 .. 64 ) )
        MAX-ACCESS    read-create
        STATUS        current
        DESCRIPTION
            "DNS name of the server host."
        ::= { aaaServerEntry 3}

    aaasIpAddress OBJECT-TYPE
        SYNTAX        IpAddress
        MAX-ACCESS    read-create
        STATUS        current
        DESCRIPTION
                "IP address of the server host."
        ::= { aaaServerEntry 4}

    aaasHostName2 OBJECT-TYPE
        SYNTAX        SnmpAdminString ( SIZE( 0 .. 64 ) )
        MAX-ACCESS    read-create
        STATUS        current
        DESCRIPTION
            "DNS name of the backup server host."
        ::= { aaaServerEntry 5}

    aaasIpAddress2 OBJECT-TYPE
        SYNTAX        IpAddress
        MAX-ACCESS    read-create
        STATUS        current
        DESCRIPTION
            "IP address of the backup server host."
        ::= { aaaServerEntry 6}

    aaasRetries OBJECT-TYPE
        SYNTAX        Integer32 ( 0 .. 32 )
        MAX-ACCESS    read-create
        STATUS        current
        DESCRIPTION
            " Number of retries the switch makes to the server to
            authenticate a user before trying the next backup server.
            The default value is 3."
        DEFVAL        { 3 }
        ::= { aaaServerEntry 7}

    aaasTimout OBJECT-TYPE
        SYNTAX        Integer32 ( 0 .. 30 )
        MAX-ACCESS    read-create
        STATUS        current
        DESCRIPTION
            "Time-out for server replies to authentication requests.
            The default value is 2."
        DEFVAL        { 2 }
        ::= { aaaServerEntry 8}

    aaasRadKey OBJECT-TYPE
        SYNTAX        SnmpAdminString ( SIZE( 0 .. 64 ) )
        MAX-ACCESS    read-create
        STATUS        current
        DESCRIPTION
            "The shared secret is a string of characters known to the switch
            and to the RADIUS server, but it is not sent out over the network.
            The secret can be any text string and must be configured here as
            well as on the server. The secret is stored encrypted using a two
            way algorithm."
        ::= { aaaServerEntry 9}


    aaasRadAuthPort OBJECT-TYPE
        SYNTAX        Integer32 ( 0 .. 65535 )
        MAX-ACCESS    read-create
        STATUS        current
        DESCRIPTION
            "For RADIUS server only.
            Port number for authentication request;
            the host is not used for authentication if set to 0.
            The default value is 1645."
        DEFVAL        { 1645 }
        ::= { aaaServerEntry 10}

    aaasRadAcctPort OBJECT-TYPE
        SYNTAX        Integer32 ( 0 .. 65535 )
        MAX-ACCESS    read-create
        STATUS        current
        DESCRIPTION
            "For RADIUS server only.
            Port number for accounting request;
            the host is not used for authentication if set to 0.
            The default value is 1646."
        DEFVAL        { 1646 }
        ::= { aaaServerEntry 11}

    aaasLdapPort OBJECT-TYPE
        SYNTAX        Integer32 ( 0 .. 65535 )
        MAX-ACCESS    read-create
        STATUS        current
        DESCRIPTION
            "For LDAP server only.
            Port number for LDAP server host."
        DEFVAL        { 0 }
        ::= { aaaServerEntry 12}

    aaasLdapDn OBJECT-TYPE
        SYNTAX        SnmpAdminString ( SIZE( 0 .. 255 ) )
        MAX-ACCESS    read-create
        STATUS        current
        DESCRIPTION
            "For LDAP server only.
            the super user dn, i.e., the administrative distinguished name
            recognized by the LDAP-enabled directory servers
            (e.g., cn=manager)"
        ::= { aaaServerEntry 13}

    aaasLdapPasswd OBJECT-TYPE
        SYNTAX        SnmpAdminString ( SIZE( 0 .. 32 ) )
        MAX-ACCESS    read-create
        STATUS        current
        DESCRIPTION
            "For LDAP server only.
            the super user password, i.e., the administrative password
            recognized by LDAP-enabled directory servers (e.g., secret).
            The secret is stored encrypted using a two way algorithm."
        ::= { aaaServerEntry 14}

    aaasLdapSearchBase OBJECT-TYPE
        SYNTAX        SnmpAdminString ( SIZE( 0 .. 64 ) )
        MAX-ACCESS    read-create
        STATUS        current
        DESCRIPTION
            "For LDAP server only.
             Search base recognized by LDAP-enabled
             directory servers (e.g.,o=company, c=US)."
        ::= { aaaServerEntry 15}

    aaasLdapServType OBJECT-TYPE
        SYNTAX        INTEGER
                      {
                                 ns(0),
                            generic(1),
                           netscape(2),
                             novell(3),
                                sun(4),
                          microsoft(5)
                      }
        MAX-ACCESS    read-create
        STATUS        current
        DESCRIPTION
            "For LDAP server only.
             Directory server type used in LDAP Authentication:
                        ns(0) - non significant value
                   generic(1) - Generic Schema
                  netscape(2) - Netscape Directory Server
                    novell(3) - Novell NDS
                       sun(4) - Sun Directory Services
                 microsoft(5) - Microsoft Active Directory"
        DEFVAL        { netscape }
        ::= { aaaServerEntry 16}

    aaasLdapEnableSsl OBJECT-TYPE
        SYNTAX        INTEGER
                      {
                             ns(0),
                           true(1),
                          false(2)
                      }
        MAX-ACCESS    read-create
        STATUS        current
        DESCRIPTION
            "Only for LDAP server.
            Specify if the connection between the swtich and the LDAP server
            use a SSL session."
        DEFVAL        { false }
        ::= { aaaServerEntry 17}


    aaasRowStatus OBJECT-TYPE
        SYNTAX        RowStatus
        MAX-ACCESS    read-create
        STATUS        current
        DESCRIPTION
            "The status of this table entry."
        DEFVAL        { notInService }
        ::= { aaaServerEntry 18}

   aaasTacacsKey OBJECT-TYPE
        SYNTAX        SnmpAdminString ( SIZE( 0 .. 64 ) )
        MAX-ACCESS    read-create
        STATUS        current
        DESCRIPTION
            "The shared secret is a string of characters known to the switch
            and to the TACACS+ server, but it is not sent out over the network.
            The secret can be any text string and must be configured here as
            well as on the server. The secret is stored encrypted using a two
            way algorithm."
        ::= { aaaServerEntry 19}


    aaasTacacsPort OBJECT-TYPE
        SYNTAX        Integer32 ( 0 .. 65535 )
        MAX-ACCESS    read-create
        STATUS        current
        DESCRIPTION
            "For TACACS+ server only.
            Port number for LDAP server host."
        DEFVAL        { 49 }
        ::= { aaaServerEntry 20}

    aaasVrfName OBJECT-TYPE
        SYNTAX        SnmpAdminString ( SIZE( 0 .. 32 ) )
        MAX-ACCESS    read-create
        STATUS        current
        DESCRIPTION
            "Name of the VRF that the server is on.
            This VRF name is valid only when the server type is RADIUS.
            (aaasProtocol = 1 (Radius)."
        ::= { aaaServerEntry 21}



--    AAA authentication accounting MIB

    aaaAuthAcctMIB    OBJECT IDENTIFIER ::= { alcatelIND1AAAMIBObjects 2 }


--
--    Authenticated switch access configuration table
--

    aaaAuthSATable OBJECT-TYPE
        SYNTAX        SEQUENCE OF AaaAuthSAEntry
        MAX-ACCESS    not-accessible
        STATUS        current
        DESCRIPTION
            "This table allow to display and modify the configuration of the
            authentication servers for the switch accesses."
        ::= { aaaAuthAcctMIB 1 }

    aaaAuthSAEntry OBJECT-TYPE
        SYNTAX        AaaAuthSAEntry
        MAX-ACCESS    not-accessible
        STATUS        current
        DESCRIPTION
            "A switch access authentication entry is specified by the type
            of access."
        INDEX { aaatsInterface}
        ::= { aaaAuthSATable 1 }

    AaaAuthSAEntry ::= SEQUENCE
        {
            aaatsInterface    INTEGER,
            aaatsName1        SnmpAdminString,
            aaatsName2        SnmpAdminString,
            aaatsName3        SnmpAdminString,
            aaatsName4        SnmpAdminString,
            aaatsRowStatus    RowStatus,
            aaatsCertificate  INTEGER
        }

    aaatsInterface OBJECT-TYPE
        SYNTAX        INTEGER
                      {
                          default(1),
                          console(2),
                           telnet(3),
                              ftp(4),
                             http(5),
                             snmp(6),
                              ssh(7)
                      }
        MAX-ACCESS    not-accessible
        STATUS        current
        DESCRIPTION
            "Type of connection that must be authenticated
            default(1) -define the default authentication method for console,
            telnet, ftp, snmp , http and ssh. If the operator
            interface is not especially configured the default value
            is applied to this interface."
        ::= { aaaAuthSAEntry 1}


    aaatsName1 OBJECT-TYPE
        SYNTAX        SnmpAdminString ( SIZE( 0 .. 32 ) )
        MAX-ACCESS    read-create
        STATUS        current
        DESCRIPTION
            "Name of the server.
            Special value 'local' correspond to the local database.
            Other name correspond to an index value of the aaaServerTable
            snmp entry can only use ldap server and local database."
        ::= { aaaAuthSAEntry 2}

    aaatsName2 OBJECT-TYPE
        SYNTAX        SnmpAdminString ( SIZE( 0 .. 32 ) )
        MAX-ACCESS    read-create
        STATUS        current
        DESCRIPTION
            "Name of a server used if the precedent is not accessible.
            Special value 'local' correspond to the local database.
            Other name correspond to an index value of the aaaServerTable
            snmp entry can only use ldap server and local database."
        DEFVAL { "" }
        ::= { aaaAuthSAEntry 3}

    aaatsName3 OBJECT-TYPE
        SYNTAX        SnmpAdminString ( SIZE( 0 .. 32 ) )
        MAX-ACCESS    read-create
        STATUS        current
        DESCRIPTION
            "Name of a server used if the precedent is not accessible.
            Special value 'local' correspond to the local database.
            Other name correspond to an index value of the aaaServerTable
            snmp entry can only use ldap server and local database."
        DEFVAL { "" }
        ::= { aaaAuthSAEntry 4}

    aaatsName4 OBJECT-TYPE
        SYNTAX        SnmpAdminString ( SIZE( 0 .. 32 ) )
        MAX-ACCESS    read-create
        STATUS        current
        DESCRIPTION
            "Name of a server used if the precedent is not accessible.
            Special value 'local' correspond to the local database.
            Other name correspond to an index value of the aaaServerTable
            snmp entry can only use ldap server and local database."
        DEFVAL { "" }
        ::= { aaaAuthSAEntry 5}

    aaatsRowStatus OBJECT-TYPE
        SYNTAX        RowStatus
        MAX-ACCESS    read-create
        STATUS        current
        DESCRIPTION
            "The status of this table entry."
        DEFVAL        { notInService }
        ::= { aaaAuthSAEntry 7}

   aaatsCertificate OBJECT-TYPE
        SYNTAX        INTEGER
                      {
                        noCertificate(0),
                        certificateOnly(1),
                        certificateWithPassword(2)
                      }
        MAX-ACCESS    read-create
        STATUS        current
        DESCRIPTION
            "use of x509 user certificate during the HTTPs session establisment.
            noCertificate(0)- no user certificate is required,
            certificateOnly(1) - the DN from the certifiicate is used to access to the authorization
            data of the user
            certificateWithPassword(2) - the user must execute a log-in procedure with user
            name and password after his certificate validation"
            DEFVAL        { noCertificate }
            ::= { aaaAuthSAEntry 8}


--
--    Accounting configuration table for switch accesses
--

    aaaAcctSATable OBJECT-TYPE
        SYNTAX        SEQUENCE OF AaaAcctSAEntry
        MAX-ACCESS    not-accessible
        STATUS        current
        DESCRIPTION
            "This table shows current configuration for Switch access accounting."
    ::= { aaaAuthAcctMIB 2 }

    aaaAcctSAEntry OBJECT-TYPE
        SYNTAX        AaaAcctSAEntry
        MAX-ACCESS    not-accessible
        STATUS        current
        DESCRIPTION
            "Accounting configuration for switch access."
        INDEX     { aaacsInterface }
        ::= { aaaAcctSATable 1 }

    AaaAcctSAEntry ::= SEQUENCE
        {
            aaacsInterface    Integer32,
            aaacsName1        SnmpAdminString,
            aaacsName2        SnmpAdminString,
            aaacsName3        SnmpAdminString,
            aaacsName4        SnmpAdminString,
            aaacsRowStatus    RowStatus
        }

    aaacsInterface OBJECT-TYPE
        SYNTAX        Integer32 ( 1 .. 1 )
        MAX-ACCESS    not-accessible
        STATUS        current
        DESCRIPTION
            "For now, accounting for console, telnet, ftp, http, snmp, ssh are stored
            in the same set of servers, the index is always (1)."
        DEFVAL        { 1 }
        ::= { aaaAcctSAEntry 1}


    aaacsName1 OBJECT-TYPE
        SYNTAX        SnmpAdminString ( SIZE( 0 .. 32 ) )
        MAX-ACCESS    read-create
        STATUS        current
        DESCRIPTION
            "Name of the server.
            Special value 'local' correspond to the local log.
            Other name correspond to an index value of the aaaServerTable
            An Ace server can not be used for accounting."
        ::= { aaaAcctSAEntry 2}

    aaacsName2 OBJECT-TYPE
        SYNTAX        SnmpAdminString ( SIZE( 0 .. 32 ) )
        MAX-ACCESS    read-create
        STATUS        current
        DESCRIPTION
            "Name of a server used if the precedent is not accessible.
            Special value 'local' correspond to the local log.
            Other name correspond to an index value of the aaaServerTable
            An Ace server can not be used for accounting."
        DEFVAL { "" }
        ::= { aaaAcctSAEntry 3}

    aaacsName3 OBJECT-TYPE
        SYNTAX        SnmpAdminString ( SIZE( 0 .. 32 ) )
        MAX-ACCESS    read-create
        STATUS        current
        DESCRIPTION
            "Name of a server used if the precedent is not accessible.
            Special value 'local' correspond to the local log.
            Other name correspond to an index value of the aaaServerTable
            An Ace server can not be used for accounting."
        DEFVAL { "" }
    ::= { aaaAcctSAEntry 4}

    aaacsName4 OBJECT-TYPE
        SYNTAX        SnmpAdminString ( SIZE( 0 .. 32 ) )
        MAX-ACCESS    read-create
        STATUS        current
        DESCRIPTION
            "Name of a server used if the precedent is not accessible.
            Special value 'local' correspond to the local log.
            Other name correspond to an index value of the aaaServerTable
            An Ace server can not be used for accounting."
        DEFVAL { "" }
    ::= { aaaAcctSAEntry 5}

    aaacsRowStatus OBJECT-TYPE
        SYNTAX        RowStatus
        MAX-ACCESS    read-create
        STATUS        current
        DESCRIPTION
            "The status of this table entry."
        DEFVAL        { notInService }
        ::= { aaaAcctSAEntry 6}




--
--    Accounting configuration table for commands
--
    aaaAcctCmdTable OBJECT-TYPE
        SYNTAX        SEQUENCE OF AaaAcctCmdEntry
        MAX-ACCESS    not-accessible
        STATUS        current
        DESCRIPTION
            "This table stores the commands that will be logged during an accounting session.
                         This feature is valid only for Tacacs+ accounting"
    ::= { aaaAuthAcctMIB 3 }

    aaaAcctCmdEntry OBJECT-TYPE
        SYNTAX        AaaAcctCmdEntry
        MAX-ACCESS    not-accessible
        STATUS        current
        DESCRIPTION
            "Tacacs+ Accounting configuration for executed commands."
        INDEX     { aaacmdInterface }
        ::= { aaaAcctCmdTable 1 }

    AaaAcctCmdEntry ::= SEQUENCE
        {
            aaacmdInterface       Integer32,
            aaacmdSrvName1        SnmpAdminString,
            aaacmdSrvName2        SnmpAdminString,
            aaacmdSrvName3        SnmpAdminString,
            aaacmdSrvName4        SnmpAdminString,
            aaacmdRowStatus       RowStatus
        }

    aaacmdInterface OBJECT-TYPE
        SYNTAX        Integer32 ( 1 .. 1 )
        MAX-ACCESS    not-accessible
        STATUS        current
        DESCRIPTION
            "For now, accounting for console, telnet, ftp, http, snmp, ssh are stored
            in the same set of servers, the index is always (1)."
        DEFVAL        { 1 }
        ::= { aaaAcctCmdEntry 1}


    aaacmdSrvName1 OBJECT-TYPE
        SYNTAX        SnmpAdminString ( SIZE( 0 .. 32 ) )
        MAX-ACCESS    read-create
        STATUS        current
        DESCRIPTION
            "Name of the Tacacs+ server.
            Other name correspond to an index value of the aaaServerTable"
        ::= { aaaAcctCmdEntry 2}

    aaacmdSrvName2 OBJECT-TYPE
        SYNTAX        SnmpAdminString ( SIZE( 0 .. 32 ) )
        MAX-ACCESS    read-create
        STATUS        current
        DESCRIPTION
            "Name of the Tacacs+  server used if the precedent is not accessible.
            Other name correspond to an index value of the aaaServerTable"
        DEFVAL { "" }
        ::= { aaaAcctCmdEntry 3}

    aaacmdSrvName3 OBJECT-TYPE
        SYNTAX        SnmpAdminString ( SIZE( 0 .. 32 ) )
        MAX-ACCESS    read-create
        STATUS        current
        DESCRIPTION
            "Name of the Tacacs+  server used if the precedent is not accessible.
            Other name correspond to an index value of the aaaServerTable"
        DEFVAL { "" }
    ::= { aaaAcctCmdEntry 4}

    aaacmdSrvName4 OBJECT-TYPE
        SYNTAX        SnmpAdminString ( SIZE( 0 .. 32 ) )
        MAX-ACCESS    read-create
        STATUS        current
        DESCRIPTION
            "Name of the Tacacs+ server used if the precedent is not accessible.
            Other name correspond to an index value of the aaaServerTable"
        DEFVAL { "" }
    ::= { aaaAcctCmdEntry 5}

    aaacmdRowStatus OBJECT-TYPE
        SYNTAX        RowStatus
        MAX-ACCESS    read-create
        STATUS        current
        DESCRIPTION
            "The status of this table entry."
        DEFVAL        { notInService }
        ::= { aaaAcctCmdEntry 6}

--
--    Authenticated Device configuration table
--

   aaaAuthDATable  OBJECT-TYPE
        SYNTAX        SEQUENCE OF AaaAuthDAEntry
        MAX-ACCESS    not-accessible
        STATUS        current
        DESCRIPTION
            "This table shows current configuration for MAC/802.1X authentication."
    ::= { aaaAuthAcctMIB 4 }

    aaaAuthDAEntry OBJECT-TYPE
        SYNTAX        AaaAuthDAEntry
        MAX-ACCESS    not-accessible
        STATUS        current
        DESCRIPTION
            "configuration for MAC/802.1X authentication."
        INDEX     { aaadaInterface }
        ::= { aaaAuthDATable 1 }

    AaaAuthDAEntry ::= SEQUENCE
        {
            aaadaInterface    INTEGER,
            aaadaName1        SnmpAdminString,
            aaadaName2        SnmpAdminString,
            aaadaName3        SnmpAdminString,
            aaadaName4        SnmpAdminString,
            aaadaRowStatus    RowStatus
        }


    aaadaInterface OBJECT-TYPE
        SYNTAX        INTEGER ( 1 .. 2 )
        MAX-ACCESS    read-create
        STATUS        current
        DESCRIPTION
            "one for mac, two for 1x."
        DEFVAL        { 1 }
        ::= { aaaAuthDAEntry 1}


    aaadaName1 OBJECT-TYPE
        SYNTAX        SnmpAdminString ( SIZE( 0 .. 32 ) )
        MAX-ACCESS    read-create
        STATUS        current
        DESCRIPTION
            "Name of the server.
            It corresponds to an index value of the aaaServerTable
            Only RADIUS server can be used in front hand."
        ::= { aaaAuthDAEntry 2}

    aaadaName2 OBJECT-TYPE
        SYNTAX        SnmpAdminString ( SIZE( 0 .. 32 ) )
        MAX-ACCESS    read-create
        STATUS        current
        DESCRIPTION
            "Name of the server.
            It corresponds to an index value of the aaaServerTable
            Only RADIUS server can be used in front hand."
        DEFVAL { "" }

        ::= { aaaAuthDAEntry 3}

    aaadaName3 OBJECT-TYPE
        SYNTAX        SnmpAdminString ( SIZE( 0 .. 32 ) )
        MAX-ACCESS    read-create
        STATUS        current
        DESCRIPTION
            "Name of the server.
            It corresponds to an index value of the aaaServerTable
            Only RADIUS server can be used in front hand."
        DEFVAL { "" }
        ::= { aaaAuthDAEntry 4}

    aaadaName4 OBJECT-TYPE
        SYNTAX        SnmpAdminString ( SIZE( 0 .. 32 ) )
        MAX-ACCESS    read-create
        STATUS        current
        DESCRIPTION
            "Name of the server.
            It corresponds to an index value of the aaaServerTable
            Only RADIUS server can be used in front hand."
        DEFVAL { "" }
        ::= { aaaAuthDAEntry 5}

    aaadaRowStatus OBJECT-TYPE
        SYNTAX        RowStatus
        MAX-ACCESS    read-create
        STATUS        current
        DESCRIPTION
            "The status of this table entry."
        DEFVAL        { notInService }
        ::= { aaaAuthDAEntry 6}



--
--    user local database configuration table
--
    aaaUserMIB    OBJECT IDENTIFIER ::= { alcatelIND1AAAMIBObjects 3 }

    aaaUserTable OBJECT-TYPE
        SYNTAX        SEQUENCE OF AaaUserEntry
        MAX-ACCESS    not-accessible
        STATUS        current
        DESCRIPTION
            "This table shows current configuration for the local user database."
        ::= { aaaUserMIB 1 }

    aaaUserEntry OBJECT-TYPE
        SYNTAX        AaaUserEntry
        MAX-ACCESS    not-accessible
        STATUS        current
        DESCRIPTION
            "An user configuration identified by its user name."
        INDEX { aaauUserName }
        ::= { aaaUserTable 1 }

    AaaUserEntry ::= SEQUENCE
        {
            aaauUserName       SnmpAdminString,
            aaauPassword       SnmpAdminString,
            aaauReadRight1     Unsigned32,
            aaauReadRight2     Unsigned32,
            aaauWriteRight1    Unsigned32,
            aaauWriteRight2    Unsigned32,
            aaauSnmpLevel      INTEGER,
            aaauSnmpAuthKey    OCTET STRING,
            aaauRowStatus      RowStatus,
            aaauOldPassword    SnmpAdminString,
            aaauPasswordExpirationDate          SnmpAdminString,
            aaauPasswordExpirationInMinute      Integer32,
            aaauPasswordAllowModifyDate         SnmpAdminString,
            aaauPasswordLockoutEnable           INTEGER,
            aaauBadAtempts                      Integer32

        }

    aaauUserName OBJECT-TYPE
        SYNTAX        SnmpAdminString ( SIZE( 0 .. 63 ) )
        MAX-ACCESS    not-accessible
        STATUS        current
        DESCRIPTION
            "Name of the user."
        ::= { aaaUserEntry 1}

    aaauPassword OBJECT-TYPE
        SYNTAX        SnmpAdminString ( SIZE( 0 .. 47 ) )
        MAX-ACCESS    read-create
        STATUS        current
        DESCRIPTION
            "Password of the user. For get response the password in encoded in a
            one way method. This makes the password readable by noone."
        ::= { aaaUserEntry 2}

    aaauReadRight1 OBJECT-TYPE
        SYNTAX        Unsigned32 ( 0 .. 4294967295 )
        MAX-ACCESS    read-create
        STATUS        current
        DESCRIPTION
            "Specifies the families that the user can execute with read right.
            Each bit of the 32-bit integer mask represents a command's family
            number. When the family bit is set, the user is allowed to run
            commands of this family.First part of the bitmask.If the value is
            not specified, the value configured for the 'default' user is taken"
        ::= { aaaUserEntry 3}

    aaauReadRight2 OBJECT-TYPE
        SYNTAX        Unsigned32 ( 0 .. 4294967295 )
        MAX-ACCESS    read-create
        STATUS        current
        DESCRIPTION
            "Specifies the families that the user can execute with read right.
            Each bit of the 32-bit integer mask represents a command's family
            number. When the family bit is set, the user is allowed to run
            commands of this family.Second part of the bitmask.If the value is
            not specified, the value configured for the 'default' user is taken"
        ::= { aaaUserEntry 4}


    aaauWriteRight1 OBJECT-TYPE
        SYNTAX        Unsigned32 ( 0 .. 4294967295 )
        MAX-ACCESS    read-create
        STATUS        current
        DESCRIPTION
            "Specifies the families that the user can execute with write right.
            Each bit of the 32-bit integer mask represents a command's family
            number. When the family bit is set, the user is allowed to run commands of
            this family. First part of the bitmask.If the value is
            not specified, the value configured for the 'default' user is taken"
        ::= { aaaUserEntry 5}

    aaauWriteRight2 OBJECT-TYPE
        SYNTAX        Unsigned32 ( 0 .. 4294967295 )
        MAX-ACCESS    read-create
        STATUS        current
        DESCRIPTION
            "Specifies the families that the user can execute with write right.
            Each bit of the 32-bit integer mask represents a command's family
            number. When the family bit is set, the user is allowed to run commands of
            this family. Second part of the bitmask.If the value is
            not specified, the value configured for the 'default' user is taken"
        ::= { aaaUserEntry 6}

    aaauSnmpLevel OBJECT-TYPE
        SYNTAX        INTEGER
                      {
                               no(1),
                           noauth(2),
                              sha(3),
                              md5(4),
                          shaDes(5),
                          md5Des(6)
                      }
        MAX-ACCESS    read-create
        STATUS        current
        DESCRIPTION
            "Specifies if the user is authorized to use SNMP and if yes its security level.
                     no(1) - Not authorized to use SNMP.
                 noauth(2) - SNMPv1,SNMPv2c or SNMPv3 without authentication.
                    sha(3) - SNMPv3 with SHA authentication and no encryption.
                    md5(4) - SNMPv3 with MD5 authentication and no encryption.
                sha-des(5) - SNMPv3 with SHA authentication and encryption.
                md5-des(6) - SNMPv3 with MD5 authentication and encryption.
             If the value is not specified, the value configured for the 'default' user
             is taken"
        ::= { aaaUserEntry 7}

    aaauSnmpAuthKey OBJECT-TYPE
        SYNTAX        OCTET STRING ( SIZE( 0 .. 255 ) )
        MAX-ACCESS    read-only
        STATUS        current
        DESCRIPTION
            "Authentication key of the user. The key is encoded in a two way method.
            The encryption key is deducted from this key."
        ::= { aaaUserEntry 8}

    aaauRowStatus OBJECT-TYPE
        SYNTAX        RowStatus
        MAX-ACCESS    read-create
        STATUS        current
        DESCRIPTION
            "The status of this table entry."
        DEFVAL        { notInService }
        ::= { aaaUserEntry 9}

    aaauOldPassword OBJECT-TYPE
        SYNTAX        SnmpAdminString ( SIZE( 0 .. 47 ) )
        MAX-ACCESS    read-create
        STATUS        current
        DESCRIPTION
            "Internal use"
        ::= { aaaUserEntry 10}

    aaauPasswordExpirationDate OBJECT-TYPE
        SYNTAX        SnmpAdminString ( SIZE( 0 .. 16 ) )
        MAX-ACCESS    read-create
        STATUS        current
        DESCRIPTION
            "The local time of when the password would be expired.
             This date will be reset once the value of
             aaaAsaDefaultPasswordExpirationInDays is updated.

             Only the following format is valid:

             mm/dd/yyyy hh:mm

             where
             mm   - month  (1-12)
             dd   - day    (1-31)
             yyyy - year   (2000-2050)
             hh   - hour   (1-24)
             mm   - minute (1-59)

             Password will not be expired if set to empty string"
        ::= { aaaUserEntry 11}

    aaauPasswordExpirationInMinute OBJECT-TYPE
        SYNTAX        Integer32 ( -1 .. 216000 )
        MAX-ACCESS    read-create
        STATUS        current
        DESCRIPTION
            "Number of minutes from now till the password expiration time.
             Setting this object will update aaauPasswordExpirationDate.
             If -1, password will not be expired.
             If  0, password has been expired."
        ::= { aaaUserEntry 12}

     aaauPasswordAllowModifyDate OBJECT-TYPE
        SYNTAX        SnmpAdminString ( SIZE( 0 .. 16 ) )
        MAX-ACCESS    read-only
        STATUS        current
        DESCRIPTION
            "The local time of when the password can be start to be modified.
             This date will be reset once the value of
             aaauPasswordAllowModifyDate is updated.

             Only the following format is valid:

             mm/dd/yyyy hh:mm

             where
             mm   - month  (1-12)
             dd   - day    (1-31)
             yyyy - year   (2000-2050)
             hh   - hour   (1-24)
             mm   - minute (1-59)

             Password will not be expired if set to empty string"
        ::= { aaaUserEntry 13}

     aaauPasswordLockoutEnable OBJECT-TYPE
        SYNTAX        INTEGER {lockout(1),unlock(2),expired(3)}
        MAX-ACCESS    read-create
        STATUS        current
        DESCRIPTION
            "Indicate whether this account is locked out."
            DEFVAL { unlock }
        ::= { aaaUserEntry 14}

     aaauBadAtempts OBJECT-TYPE
        SYNTAX        Integer32 ( 0 .. 999 )
        MAX-ACCESS    read-only
        STATUS        current
        DESCRIPTION
            "Number bad password attempts in the observation window."
            DEFVAL { 0 }
        ::= { aaaUserEntry 15}



--    ASA specific configuration MIB

    aaaAsaConfig    OBJECT IDENTIFIER ::= { alcatelIND1AAAMIBObjects 4 }

--
--    ASA configuration group
--

    aaaAsaPasswordSizeMin OBJECT-TYPE
        SYNTAX        Integer32 ( 0 .. 14 )
        MAX-ACCESS    read-write
        STATUS        current
        DESCRIPTION
            "Minimum number of digits of the passwords
            ( nominator aaauPassword)."
          DEFVAL     { 0 }
        ::= { aaaAsaConfig 1}

    aaaAsaDefaultPasswordExpirationInDays OBJECT-TYPE
        SYNTAX        Integer32 ( 0 .. 150 )
        MAX-ACCESS    read-write
        STATUS        current
        DESCRIPTION
            "Default password expiration time in days to be applied to all users.
             Updating this object will reset aaauPasswordExpirationDate.
             Password expiration will not be enforced if set to 0."
          DEFVAL     { 0 }
        ::= { aaaAsaConfig 2}

   aaaAsaPasswordContainUserName OBJECT-TYPE
        SYNTAX        INTEGER {enable(1),disable(2)}
        MAX-ACCESS    read-write
        STATUS        current
        DESCRIPTION
            "Indicate whether check password contains username or not."
            DEFVAL { disable }
        ::= { aaaAsaConfig 3}

   aaaAsaPasswordMinUpperCase OBJECT-TYPE
        SYNTAX        Integer32 ( 0 .. 7 )
        MAX-ACCESS    read-write
        STATUS        current
        DESCRIPTION
            "Minimum number of English uppercase characters required for password. 0 is disable"
            DEFVAL     { 0 }
        ::= { aaaAsaConfig 4}

   aaaAsaPasswordMinLowerCase OBJECT-TYPE
        SYNTAX        Integer32 ( 0 .. 7 )
        MAX-ACCESS    read-write
        STATUS        current
        DESCRIPTION
            "Minimum number of English lowercase characters required for password 0 is disable."
            DEFVAL     { 0 }
        ::= { aaaAsaConfig 5}

    aaaAsaPasswordMinDigit OBJECT-TYPE
        SYNTAX        Integer32 ( 0 .. 7 )
        MAX-ACCESS    read-write
        STATUS        current
        DESCRIPTION
            "Minimum number of base-10 digits required for password. 0 is disable"
            DEFVAL     { 0 }
        ::= { aaaAsaConfig 6}

    aaaAsaPasswordMinNonAlphan OBJECT-TYPE
        SYNTAX        Integer32 ( 0 .. 7 )
        MAX-ACCESS    read-write
        STATUS        current
        DESCRIPTION
            "Minimum number of non-alphanumeric required for password. 0 is disable"
            DEFVAL     { 0 }
        ::= { aaaAsaConfig 7}

    aaaAsaPasswordHistory OBJECT-TYPE
        SYNTAX        Integer32 ( 0 .. 24 )
        MAX-ACCESS    read-write
        STATUS        current
        DESCRIPTION
            "Password history feature will prevent users from repeatedly using the same password. 0 is disable"
            DEFVAL     { 4 }
        ::= { aaaAsaConfig 8}

  aaaAsaPasswordMinAge OBJECT-TYPE
        SYNTAX        Integer32 ( 0 .. 150 )
        MAX-ACCESS    read-write
        STATUS        current
        DESCRIPTION
            "The password can't be modified in these days. 0 is disable"
            DEFVAL     { 0 }
        ::= { aaaAsaConfig 9}

   aaaAsaLockoutWindow OBJECT-TYPE
        SYNTAX        Integer32 ( 0 .. 99999 )
        MAX-ACCESS    read-write
        STATUS        current
        DESCRIPTION
            "The window of time in which the system increments the bad logon count.(minutes) 0 is disable"
        DEFVAL        { 0 }
        ::= { aaaAsaConfig 10}

   aaaAsaLockoutDuration OBJECT-TYPE
        SYNTAX        Integer32 ( 0 .. 99999 )
        MAX-ACCESS    read-write
        STATUS        current
        DESCRIPTION
            "The amount of time that an account is locked due to the aaauLockoutThreshold being exceeded.(minutes) 0 is disable"
        DEFVAL        { 0 }
        ::= { aaaAsaConfig 11}

   aaaAsaLockoutThreshold OBJECT-TYPE
        SYNTAX        Integer32 ( 0 .. 999 )
        MAX-ACCESS    read-write
        STATUS        current
        DESCRIPTION
             "The number of invalid logon attempts that are permitted before the account is locked out. 0 is disable"
        DEFVAL        { 0 }
        ::= { aaaAsaConfig 12}

    aaaAsaAccessPolicyAdminConsoleOnly OBJECT-TYPE
        SYNTAX        INTEGER {enable(1),disable(2)}
        MAX-ACCESS    read-write
        STATUS        current
        DESCRIPTION
             "Enable or disable AdminUser console only restriction"
        DEFVAL { disable }
        ::= { aaaAsaConfig 13}


--
-- Compliance Statements
--

    alcatelIND1AAAMIBCompliance MODULE-COMPLIANCE
        STATUS  current
        DESCRIPTION
            "Compliance statement for
             Authentication, Authorization, and Accounting (AAA) Subsystem."
        MODULE  -- this module

            MANDATORY-GROUPS
            {
                aaaServerMIBGroup,
                aaaAuthAcctGroup,
                aaaUserMIBGroup
            }

        ::= { alcatelIND1AAAMIBCompliances 1 }


--
-- Units Of Conformance
--

    aaaServerMIBGroup OBJECT-GROUP
        OBJECTS
        {
            aaasProtocol,           -- Server configuration table
            aaasHostName,
            aaasIpAddress,
            aaasHostName2,
            aaasIpAddress2,
            aaasRetries,
            aaasTimout,
            aaasRadKey,
            aaasRadAuthPort,
            aaasRadAcctPort,
            aaasLdapPort,
            aaasLdapDn,
            aaasLdapPasswd,
            aaasLdapSearchBase,
            aaasLdapServType,
            aaasLdapEnableSsl,
            aaasRowStatus,
            aaasTacacsKey,
            aaasTacacsPort,
            aaasVrfName
        }
        STATUS  current
        DESCRIPTION
            "Collection of objects for management of AAA Server."
        ::= { alcatelIND1AAAMIBGroups 1 }


    aaaAuthAcctGroup OBJECT-GROUP
        OBJECTS
        {
            -- Authenticated switch access configuration table
            aaatsName1,
            aaatsName2,
            aaatsName3,
            aaatsName4,
            aaatsRowStatus,
            aaatsCertificate,

            -- Accounting configuration table for switch accesses
            aaacsName1,
            aaacsName2,
            aaacsName3,
            aaacsName4,
            aaacsRowStatus,

            aaacmdSrvName1,
            aaacmdSrvName2,
            aaacmdSrvName3,
            aaacmdSrvName4,
            aaacmdRowStatus,

	    -- Device Authentication
            aaadaInterface,
            aaadaName1,
            aaadaName2,
            aaadaName3,
            aaadaName4,
            aaadaRowStatus

}
        STATUS  current
        DESCRIPTION
            "Collection of objects for management of AAA Authentication Accounting."
        ::= { alcatelIND1AAAMIBGroups 2 }


    aaaUserMIBGroup OBJECT-GROUP
        OBJECTS
        {
                -- User local database configuration table
                aaauPassword,
                aaauReadRight1,
                aaauReadRight2,
                aaauWriteRight1,
                aaauWriteRight2,
                aaauSnmpLevel,
                aaauSnmpAuthKey,
                aaauRowStatus,
                aaauOldPassword,
                aaauPasswordExpirationDate,
                aaauPasswordExpirationInMinute,
                aaauPasswordAllowModifyDate,
                aaauPasswordLockoutEnable ,
                aaauBadAtempts,
                aaaAsaPasswordSizeMin, -- ASA specific configuration MIB
                aaaAsaDefaultPasswordExpirationInDays,
                aaaAsaPasswordContainUserName,
                aaaAsaPasswordMinUpperCase,
                aaaAsaPasswordMinLowerCase,
                aaaAsaPasswordMinDigit,
                aaaAsaPasswordMinNonAlphan,
                aaaAsaPasswordHistory,
                aaaAsaPasswordMinAge,
                aaaAsaLockoutWindow,
                aaaAsaLockoutDuration,
                aaaAsaLockoutThreshold,
                aaaAsaAccessPolicyAdminConsoleOnly
        }
        STATUS  current
        DESCRIPTION
            "Collection of objects for management of AAA User Local Database."
        ::= { alcatelIND1AAAMIBGroups 3 }


END
