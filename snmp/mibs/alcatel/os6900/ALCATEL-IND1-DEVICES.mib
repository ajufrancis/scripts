ALCATEL-IND1-DEVICES DEFINITIONS ::= BEGIN


IMPORTS
    MODULE-IDENTITY, OBJECT-IDENTITY
FROM
    SNMPv2-SMI

    hardwareIND1Devices
FROM
    ALCATEL-IND1-BASE;


alcatelIND1DevicesMIB MODULE-IDENTITY

    LAST-UPDATED  "201003010000Z"
    ORGANIZATION  "Alcatel-Lucent"
    CONTACT-INFO
        "Please consult with Customer Service to ensure the most appropriate
         version of this document is used with the products in question:

                    Alcatel-Lucent, Enterprise Solutions Division
                   (Formerly Alcatel Internetworking, Incorporated)
                           26801 West Agoura Road
                        Agoura Hills, CA  91301-5122
                          United States Of America

        Telephone:               North America  +1 800 995 2696
                                 Latin America  +1 877 919 9526
                                 Europe         +31 23 556 0100
                                 Asia           +65 394 7933
                                 All Other      +1 818 878 4507

        Electronic Mail:         support@ind.alcatel.com
        World Wide Web:          http://alcatel-lucent.com/wps/portal/enterprise
        File Transfer Protocol:  ftp://ftp.ind.alcatel.com/pub/products/mibs"

    DESCRIPTION
        "This module describes an authoritative enterprise-specific Simple
         Network Management Protocol (SNMP) Management Information Base (MIB):

             This module provides Object Indentifier definitions for
             Chassis and Modules of the Alcatel Internetworking
             OmniSwitch 10000 Series Product Lines.

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

                     Copyright (C) 1995-2010 Alcatel-Lucent
                         ALL RIGHTS RESERVED WORLDWIDE"

    REVISION      "201003010000Z"
    DESCRIPTION
        "Initial version of this MIB Module."

    ::= { hardwareIND1Devices 1 }


familyOmniSwitch10000 OBJECT-IDENTITY
    STATUS current
    DESCRIPTION
        "Branch For OmniSwitch 10000 Series Product Family."
    ::= { alcatelIND1DevicesMIB 9 }

chassisOmniSwitch10000 OBJECT-IDENTITY
    STATUS current
    DESCRIPTION
        "Branch For OmniSwitch 10000 Series Chassis."
    ::= { familyOmniSwitch10000 1 }

deviceOmniSwitch10000 OBJECT-IDENTITY
    STATUS current
    DESCRIPTION
        "OmniSwitch 10000 8-Slot Chassis.
        Model Name: OS10000
        Assembly:
        sysObjectID: 1.3.6.1.4.1.6486.801.1.1.2.1.9.1.1"
    ::= { chassisOmniSwitch10000 1 }

fansOmniSwitch10000 OBJECT-IDENTITY
    STATUS current
    DESCRIPTION
        "Branch For OmniSwitch 10000 Series Fan Trays."
    ::= { familyOmniSwitch10000 2 }

powersOmniSwitch10000 OBJECT-IDENTITY
    STATUS current
    DESCRIPTION
        "Branch For OmniSwitch 10000 Series Power Supplies."
    ::= { familyOmniSwitch10000 3 }

modulesOmniSwitch10000 OBJECT-IDENTITY
    STATUS current
    DESCRIPTION
        "Branch For OmniSwitch 10000 Series Modules."
    ::= { familyOmniSwitch10000 4 }

modulesOmniSwitch10000CM OBJECT-IDENTITY
    STATUS current
    DESCRIPTION
        "Branch For OmniSwitch 10000 Series Chassis Management (CM) Modules."
    ::= { modulesOmniSwitch10000 1 }

cmmOmniSwitch10000 OBJECT-IDENTITY
    STATUS current
    DESCRIPTION
        "OmniSwitch 10000 Series Chassis Management Module.
        Model Name: OS10000-CMM
        Assembly:
        sysObjectID: 1.3.6.1.4.1.6486.801.1.1.2.1.9.4.1.1"
    ::= { modulesOmniSwitch10000CM 1 }

cmmOmniSwitch10000PROC OBJECT-IDENTITY
    STATUS current
    DESCRIPTION
        "OmniSwitch 10000 Series Chassis Management Module Processor.
        Model Name: OS10000-CMM Processor
        Assembly:
        sysObjectID: 1.3.6.1.4.1.6486.801.1.1.2.1.9.4.1.1.1"
    ::= { cmmOmniSwitch10000 1 }

modulesOmniSwitch10000NI OBJECT-IDENTITY
    STATUS current
    DESCRIPTION
        "OmniSwitch 10000 Series Network Interface (NI) Modules."
    ::= { modulesOmniSwitch10000 2 }

niOmniSwitch10000GNI OBJECT-IDENTITY
    STATUS current
    DESCRIPTION
        "OmniSwitch 10000 Series 1000BaseX Ethernet Network Interface (GNI) Modules."
    ::= { modulesOmniSwitch10000NI 1 }

gniOmniSwitch10000C48 OBJECT-IDENTITY
    STATUS current
    DESCRIPTION
        "OmniSwitch 10000 Series .
        Model Name: OS10-GNI-C48
        Assembly:
        sysObjectID: 1.3.6.1.4.1.6486.801.1.1.2.1.9.4.2.1.1"
    ::= { niOmniSwitch10000GNI 1 }

gniOmniSwitch10000U48 OBJECT-IDENTITY
    STATUS current
    DESCRIPTION
        "OmniSwitch 10000 Series Ethernet Network Interface Module.
        Model Name: OS10-GNI-U48
        Assembly:
        sysObjectID: 1.3.6.1.4.1.6486.801.1.1.2.1.9.4.2.1.2"
    ::= { niOmniSwitch10000GNI 2 }

niOmniSwitch10000XNI OBJECT-IDENTITY
    STATUS current
    DESCRIPTION
        "OmniSwitch 10000 Series 10 gig Ethernet Network Interface (XNI) Modules."
    ::= { modulesOmniSwitch10000NI 2 }

gniOmniSwitch10000X16M OBJECT-IDENTITY
    STATUS current
    DESCRIPTION
        "OmniSwitch 10000 Series .
        Model Name: OS10-XNI-U32-MAIN
        Assembly:
        sysObjectID: 1.3.6.1.4.1.6486.801.1.1.2.1.9.4.2.2.1"
    ::= { niOmniSwitch10000XNI 1 }

gniOmniSwitch10000X32M OBJECT-IDENTITY
    STATUS current
    DESCRIPTION
        "OmniSwitch 10000 Series Ethernet Network Interface Module.
        Model Name: OS10-XNI-U32-MAIN
        Assembly:
        sysObjectID: 1.3.6.1.4.1.6486.801.1.1.2.1.9.4.2.2.2"
    ::= { niOmniSwitch10000XNI 2 }

cfmOmniSwitch10000 OBJECT-IDENTITY
    STATUS current
    DESCRIPTION
        "OmniSwitch 10000 Series Fabric Modules."
    ::= { modulesOmniSwitch10000 3 }

familyOmniSwitch6900 OBJECT-IDENTITY
    STATUS current
    DESCRIPTION
        "Branch For OmniSwitch 6900 Series Product Family."
    ::= { alcatelIND1DevicesMIB 10 }

chassisOmniSwitch6900 OBJECT-IDENTITY
    STATUS current
    DESCRIPTION
        "Branch For OmniSwitch 6900 1-Slot Chassis.
        Model Name: OS6900
        Assembly:
	sysObjectID: 1.3.6.1.4.1.6486.801.1.1.2.1.10.1"
    ::= { familyOmniSwitch6900 1 }

deviceOmniSwitch6900X20 OBJECT-IDENTITY
    STATUS current
    DESCRIPTION
        "OmniSwitch 6900 Series .
        Model Name: OS6900-X20
        Assembly:
        sysObjectID: 1.3.6.1.4.1.6486.801.1.1.2.1.10.1.1"
    ::= { chassisOmniSwitch6900 1 }

deviceOmniSwitch6900X40 OBJECT-IDENTITY
    STATUS current
    DESCRIPTION
        "OmniSwitch 6900 Series .
        Model Name: OS6900-X40
        Assembly:
        sysObjectID: 1.3.6.1.4.1.6486.801.1.1.2.1.10.1.2"
    ::= { chassisOmniSwitch6900 2 }

fansOmniSwitch6900 OBJECT-IDENTITY
    STATUS current
    DESCRIPTION
        "Branch For OmniSwitch 6900 Series Fan Trays."
    ::= { familyOmniSwitch6900 2 }

powersOmniSwitch6900 OBJECT-IDENTITY
    STATUS current
    DESCRIPTION
        "Branch For OmniSwitch 6900 Series Power Supplies."
    ::= { familyOmniSwitch6900 3 }


powersOmniSwitch6900AC OBJECT-IDENTITY
    STATUS current
    DESCRIPTION
        "OmniSwitch 6900 Series AC power supply FR (evacuate).
        Model Name: OS6900_PS_450W_AC
        Assembly:
        sysObjectID: 1.3.6.1.4.1.6486.801.1.1.2.1.10.3.1"
    ::= { powersOmniSwitch6900 1 }

powersOmniSwitch6900DC OBJECT-IDENTITY
    STATUS current
    DESCRIPTION
        "OmniSwitch 6900 Series DC power supply FR(evacuate).
        Model Name: OS6900_PS_450W_DC
        Assembly:
        sysObjectID: 1.3.6.1.4.1.6486.801.1.1.2.1.10.3.2"
    ::= { powersOmniSwitch6900 2 }

powersOmniSwitch6900ACRF OBJECT-IDENTITY
    STATUS current
    DESCRIPTION
        "OmniSwitch 6900 Series AC power supply RF (pressurized).
        Model Name: OS6900_PS_450W_ACRF
        Assembly:
        sysObjectID: 1.3.6.1.4.1.6486.801.1.1.2.1.10.3.3"
    ::= { powersOmniSwitch6900 3 }

powersOmniSwitch6900DCRF OBJECT-IDENTITY
    STATUS current
    DESCRIPTION
        "OmniSwitch 6900 Series DC power supply RF(pressurized).
        Model Name: OS6900_PS_450W_DCRF
        Assembly:
        sysObjectID: 1.3.6.1.4.1.6486.801.1.1.2.1.10.3.4"
    ::= { powersOmniSwitch6900 4 }

modulesOmniSwitch6900 OBJECT-IDENTITY
    STATUS current
    DESCRIPTION
        "Branch For OmniSwitch 6900 Series Modules."
    ::= { familyOmniSwitch6900 4 }

daughterBoardOmniSwitch6900 OBJECT-IDENTITY
    STATUS current
    DESCRIPTION
        "Branch For OmniSwitch 6900 Series daughter board."
    ::= { familyOmniSwitch6900 5 }

daughterBoardOmniSwitch6900XNI-U12 OBJECT-IDENTITY
    STATUS current
    DESCRIPTION
        "OmniSwitch 6900 Series daughter board U12D.
        Model Name: OS6900-XNI-U12 
        Assembly:
        sysObjectID: 1.3.6.1.4.1.6486.801.1.1.2.1.10.5.1"
    ::= { daughterBoardOmniSwitch6900 1 }

daughterBoardOmniSwitch6900XNI-U4 OBJECT-IDENTITY
    STATUS current
    DESCRIPTION
        "OmniSwitch 6900 Series daughter board U4D.
        Model Name: OS6900-XNI-U4 
        Assembly:
        sysObjectID: 1.3.6.1.4.1.6486.801.1.1.2.1.10.5.2"
    ::= { daughterBoardOmniSwitch6900 2 }

daughterBoardOmniSwitch6900QNI-U3 OBJECT-IDENTITY
    STATUS current
    DESCRIPTION
        "OmniSwitch 6900 Series daughter board U3D.
	Model Name: OS6900-QNI-U3
        Assembly:
        sysObjectID: 1.3.6.1.4.1.6486.801.1.1.2.1.10.5.3"
    ::= { daughterBoardOmniSwitch6900 3 }

daughterBoardOmniSwitch6900HNI-U6 OBJECT-IDENTITY
    STATUS current
    DESCRIPTION
        "OmniSwitch 6900 Series daughter board U6D.
        Model Name: OS6900-HNI-U6
        Assembly:
        sysObjectID: 1.3.6.1.4.1.6486.801.1.1.2.1.10.5.4"
    ::= { daughterBoardOmniSwitch6900 4 }
END
