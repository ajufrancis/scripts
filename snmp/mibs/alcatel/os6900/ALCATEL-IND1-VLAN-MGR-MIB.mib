ALCATEL-IND1-VLAN-MGR-MIB DEFINITIONS ::= BEGIN

    IMPORTS
        RowStatus, TEXTUAL-CONVENTION                   FROM SNMPv2-TC
        SnmpAdminString                                 FROM SNMP-FRAMEWORK-MIB
        MODULE-IDENTITY, OBJECT-IDENTITY,
        OBJECT-TYPE, IpAddress, Integer32, Unsigned32   FROM SNMPv2-SMI
        MODULE-COMPLIANCE, OBJECT-GROUP                 FROM SNMPv2-CONF
        softentIND1VlanMgt                              FROM ALCATEL-IND1-BASE;


    alcatelIND1VLANMgrMIB MODULE-IDENTITY
        LAST-UPDATED "200704030000Z"
        ORGANIZATION "Alcatel-Lucent"
        CONTACT-INFO
            "Please consult with Customer Service to ensure the most appropriate
             version of this document is used with the products in question:

                        Alcatel-Lucent, Enterprise Solutions Division
                       (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"

        DESCRIPTION
            "This module describes an authoritative enterprise-specific Simple
             Network Management Protocol (SNMP) Management Information Base (MIB):

                 For the Birds Of Prey Product Line
                 Vlan Manager for the distribution of vlan configuration information,
                 including the association between vlans and ports.

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

        REVISION      "200704030000Z"
        DESCRIPTION
            "The latest version of this MIB Module."
        ::= { softentIND1VlanMgt 1}

    alcatelIND1VLANMgrMIBObjects OBJECT-IDENTITY
        STATUS current
        DESCRIPTION
            "Branch For VLAN Manager
            Subsystem Managed Objects."
        ::= { alcatelIND1VLANMgrMIB 1 }


    alcatelIND1VLANMgrMIBConformance OBJECT-IDENTITY
        STATUS current
        DESCRIPTION
            "Branch For VLAN Manager
            Subsystem Conformance Information."
        ::= { alcatelIND1VLANMgrMIB 2 }


    alcatelIND1VLANMgrMIBGroups OBJECT-IDENTITY
        STATUS current
        DESCRIPTION
            "Branch For VLAN Manager
            Subsystem Units Of Conformance."
        ::= { alcatelIND1VLANMgrMIBConformance 1 }


    alcatelIND1VLANMgrMIBCompliances OBJECT-IDENTITY
        STATUS current
        DESCRIPTION
            "Branch For VLAN Manager
            Subsystem Compliance Statements."
        ::= { alcatelIND1VLANMgrMIBConformance 2 }

-- xxxxxxxxxxxxxxxxxxxxxxxxxxxxxxxxxxxxxxxxxxxxxxxxxxxxxxxxxxxxxx

    vlanMgrVlan  OBJECT IDENTIFIER ::= { alcatelIND1VLANMgrMIBObjects 1 }

-- xxxxxxxxxxxxxxxxxxxxxxxxxxxxxxxxxxxxxxxxxxxxxxxxxxxxxxxxxxxxxx

    vlanTable  OBJECT-TYPE
        SYNTAX  SEQUENCE OF VlanEntry
        MAX-ACCESS  not-accessible
        STATUS  current
        DESCRIPTION
         "A list of Virtual LAN instances in this device."
        ::= { vlanMgrVlan 1 }

    vlanEntry  OBJECT-TYPE
        SYNTAX  VlanEntry
        MAX-ACCESS  not-accessible
        STATUS  current
        DESCRIPTION
         "A VLAN entry."
        INDEX { vlanNumber }
        ::= { vlanTable 1 }

    VlanEntry ::= SEQUENCE {
            vlanNumber
                Integer32,
            vlanDescription
                SnmpAdminString,
            vlanAdmStatus
                INTEGER,
            vlanOperStatus
                INTEGER,
            vlanStatus
                RowStatus,
            vlanRouterStatus
                INTEGER,
            vlanSrcLearningStatus
                INTEGER,
            vlanType
                INTEGER,
            vlanMtu
                Integer32
    }

    vlanNumber  OBJECT-TYPE
        SYNTAX  Integer32 (1..4094)
        MAX-ACCESS  not-accessible
        STATUS  current
        DESCRIPTION
            "The VLAN number identifying this instance. Valid
             range from 1 to 4094."
        ::= { vlanEntry 1 }

    vlanDescription  OBJECT-TYPE
        SYNTAX  SnmpAdminString (SIZE (0..32))
        MAX-ACCESS  read-create
        STATUS  current
        DESCRIPTION
            "Textual description of the VLAN instance."
        ::= { vlanEntry 2 }

    vlanAdmStatus  OBJECT-TYPE
        SYNTAX  INTEGER {
            enabled(1),
            disabled(2)
        }
        MAX-ACCESS  read-create
        STATUS  current
        DESCRIPTION
            "The administrative status which can be set by
             configuration. Disable(1) will disable ALL vports
             that are connected to this VLAN, enable(2) will enable
             ALL ports on this VLAN, delete(3) will detach and
             delete the ports/routers AND remove the VLAN."
        DEFVAL { enabled }
        ::= { vlanEntry 3 }

    vlanOperStatus  OBJECT-TYPE
        SYNTAX  INTEGER {
            active(1),
            inactive(2)
        }
        MAX-ACCESS  read-only
        STATUS  current
        DESCRIPTION
            "Provide operating status of a particular VLAN environment."
        DEFVAL { inactive }
        ::= { vlanEntry 4 }

     vlanStatus  OBJECT-TYPE
        SYNTAX  RowStatus
        MAX-ACCESS  read-create
        STATUS  current
        DESCRIPTION
            "Row status to control creation/deletion of vlans."
        ::= { vlanEntry 5 }

    vlanRouterStatus  OBJECT-TYPE
        SYNTAX  INTEGER {
            none(0),
            ipv4router(1),
            ipv6router(2),
            both(3)
        }
        MAX-ACCESS  read-only
        STATUS  current
        DESCRIPTION
            "Indicates if any IP routers are configured on this vlan."
        DEFVAL { none }
        ::= { vlanEntry 6 }

    vlanSrcLearningStatus  OBJECT-TYPE
        SYNTAX  INTEGER {
            enabled(1),
            disabled(2)
        }
        MAX-ACCESS  read-create
        STATUS  current
        DESCRIPTION
            "Indicates whether the mac learning is enabled or disabled
             on this vlan."
        DEFVAL { enabled }
        ::= { vlanEntry 7 }

    vlanType  OBJECT-TYPE
        SYNTAX  INTEGER {
            invalid(0),
            service(1),
            multicastEnt(2),
            multicastService(3),
            dynamic(4),
            standard(5),
            ipc(6),
	    vipVlan(7),
	    erpVlan(8),
	    mtpVlan(9)
        }
        MAX-ACCESS  read-create
        STATUS  current
        DESCRIPTION
            "The type of the vlan"
        DEFVAL { standard }
        ::= { vlanEntry 8 }

    vlanMtu  OBJECT-TYPE
        SYNTAX  Integer32 (512..10222)
        MAX-ACCESS  read-create
        STATUS  current
        DESCRIPTION
            "Maximum transmission unit i.e. the maximum size of packet that this
             vlan can handle. It ranges from 512 to 1500 (for OS6XXX) and 10222
             (for OS7XXX and OS8XXX) with e2 encapsulation.With snap encapsulation
             it ranges from 512 to 1492"
        DEFVAL { 1500 }
        ::= { vlanEntry 9 }

-- xxxxxxxxxxxxxxxxxxxxxxxxxxxxxxxxxxxxxxxxxxxxxxxxxxxxxxxxxxxxxx

    vlanMgrVpa  OBJECT IDENTIFIER ::= { alcatelIND1VLANMgrMIBObjects 2 }

-- xxxxxxxxxxxxxxxxxxxxxxxxxxxxxxxxxxxxxxxxxxxxxxxxxxxxxxxxxxxxxx

    vpaTable  OBJECT-TYPE
        SYNTAX  SEQUENCE OF VpaEntry
        MAX-ACCESS  not-accessible
        STATUS  current
        DESCRIPTION
            "A list of Virtual LAN instances in this device."
        ::= { vlanMgrVpa 1 }

    vpaEntry  OBJECT-TYPE
        SYNTAX  VpaEntry
        MAX-ACCESS  not-accessible
        STATUS  current
        DESCRIPTION
            "A VLAN-Port Association (VPA) entry."
        INDEX { vpaVlanNumber, vpaIfIndex }
        ::= { vpaTable 1 }

    VpaEntry ::= SEQUENCE {
           vpaVlanNumber
               Integer32,
           vpaIfIndex
               Unsigned32,
           vpaType
               INTEGER,
           vpaState
               INTEGER,
           vpaStatus
               RowStatus
    }

    vpaVlanNumber  OBJECT-TYPE
        SYNTAX  Integer32 (1..4094)
        MAX-ACCESS  not-accessible
        STATUS  current
        DESCRIPTION
            "The VLAN number component of this instance. Valid
             range from 1 to 4094."
        ::= { vpaEntry 1 }

    vpaIfIndex  OBJECT-TYPE
        SYNTAX  Unsigned32 (1001..4294967295)
        MAX-ACCESS  not-accessible
        STATUS  current
        DESCRIPTION
            "The ifIndex component of this instance."
        ::= {vpaEntry 2 }

    vpaType  OBJECT-TYPE
        SYNTAX  INTEGER {
            invalid(0),
            cfgDefault(1),
            qTagged(2),
            dynamic(3),
            vstkDoubleTag(4),
            vstkTranslate(5),
            forbidden(6)
        }
        MAX-ACCESS  read-create
        STATUS  current
        DESCRIPTION
            "The type of this vpa.  Two are statically configured:
             configured default VPA and qTagged VPA.
             The other two are dynamically created according to rules/policies:
             dynamic default and mobile.  The dynamic default VPA is the
             same as a mobile VPA except that it also the default VPA for the port."
        DEFVAL { cfgDefault }
        ::= { vpaEntry 3 }

    vpaState  OBJECT-TYPE
        SYNTAX  INTEGER {
	    forwarding(0),
	    blocking(1),
	    inactive(2),
	    invalid(3)
        }
        MAX-ACCESS  read-only
        STATUS  current
        DESCRIPTION
            "The state of this vpa:
                1. inactive   - link down
                2. blocking   - link up, forwarding down
                3. forwarding - link up, forwarding up, sources learned normally
                4. filtering  - link up, forwarding up, sources filtered."
        DEFVAL { inactive }
        ::= { vpaEntry 4 }

    vpaStatus  OBJECT-TYPE
        SYNTAX  RowStatus
        MAX-ACCESS  read-create
        STATUS  current
        DESCRIPTION
            "This is used to create or delete staticPrimary VPAs (default vlans
             on a port ).  Creation replaces the existing staticPrimary VPA
             while deletion replaces the existing VPA so that the vlan number
             is 1 for the given port.  Of course the corresponding vlan and
             port must exist."
        ::= { vpaEntry 5 }


-- xxxxxxxxxxxxxxxxxxxxxxxxxxxxxxxxxxxxxxxxxxxxxxxxxxxxxxxxxxxxxx

    vlanMgrVlanSet  OBJECT IDENTIFIER ::= { alcatelIND1VLANMgrMIBObjects 3 }

-- xxxxxxxxxxxxxxxxxxxxxxxxxxxxxxxxxxxxxxxxxxxxxxxxxxxxxxxxxxxxxx

    vlanSetVlanCount  OBJECT-TYPE
        SYNTAX  Integer32 (1..4094)
        MAX-ACCESS  read-only
        STATUS  current
        DESCRIPTION
            "Count of existing VLANs on switch."
        ::= { vlanMgrVlanSet 1 }

    vlanSetDynamicVlanCount  OBJECT-TYPE
        SYNTAX  Integer32 (0..4094)
        MAX-ACCESS  read-only
        STATUS  current
        DESCRIPTION
            "Count of number of dynamic vlans in the system"
        ::= { vlanMgrVlanSet 2 }

    vlanSetIpRouterCount  OBJECT-TYPE
        SYNTAX  Integer32 (0..4094)
        MAX-ACCESS  read-only
        STATUS  current
        DESCRIPTION
            "Count of VLANs on switch with IP router port configured."
        ::= { vlanMgrVlanSet 3 }

    vlanSetVstkVlanCount  OBJECT-TYPE
	SYNTAX  Integer32 (0..4094)
	MAX-ACCESS  read-only
	STATUS  current
	DESCRIPTION
	    "Count of Vlan Stacking vlans in the system"
	::= { vlanMgrVlanSet 4 }

-- xxxxxxxxxxxxxxxxxxxxxxxxxxxxxxxxxxxxxxxxxxxxxxxxxxxxxxxxxx
-- COMPLIANCE
-- xxxxxxxxxxxxxxxxxxxxxxxxxxxxxxxxxxxxxxxxxxxxxxxx

    alcatelIND1VLANMgrMIBCompliance MODULE-COMPLIANCE
        STATUS  current
        DESCRIPTION
            "Compliance statement for
             VLAN Manager."
        MODULE
            MANDATORY-GROUPS
            {
                vlanMgrVlanGroup,
                vlanMgrVpaGroup,
                vlanMgrVlanSetGroup
            }

        ::= { alcatelIND1VLANMgrMIBCompliances 1 }


-- xxxxxxxxxxxxxxxxxxxxxxxxxxxxxxxxxxxxxxxxxxxxxxxxxxxxxxxxxx
-- UNITS OF CONFORMANCE
-- xxxxxxxxxxxxxxxxxxxxxxxxxxxxxxxxxxxxxxxxxxxxxxxxxxxxxxxxxx

    vlanMgrVlanGroup OBJECT-GROUP
        OBJECTS
        {
            vlanDescription,
            vlanAdmStatus,
            vlanOperStatus,
            vlanStatus,
            vlanRouterStatus,
            vlanSrcLearningStatus,
            vlanType,
            vlanMtu
        }
        STATUS  current
        DESCRIPTION
            "Collection of objects for management of Vlan Manager VLANs."
        ::= { alcatelIND1VLANMgrMIBGroups 1 }


    vlanMgrVpaGroup OBJECT-GROUP
        OBJECTS
        {
            vpaType,
            vpaState,
            vpaStatus
        }
        STATUS  current
        DESCRIPTION
            "Collection of objects for management of Vlan Manager VPAs."
        ::= { alcatelIND1VLANMgrMIBGroups 2 }

    vlanMgrVlanSetGroup OBJECT-GROUP
        OBJECTS
        {
           vlanSetVlanCount,
           vlanSetDynamicVlanCount,
           vlanSetIpRouterCount,
           vlanSetVstkVlanCount
        }
        STATUS current
        DESCRIPTION
            "Collection of objects for Vlan Manager global properties."
        ::= { alcatelIND1VLANMgrMIBGroups 3 }

END
