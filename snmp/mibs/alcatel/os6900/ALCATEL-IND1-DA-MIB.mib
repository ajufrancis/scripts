ALCATEL-IND1-DA-MIB DEFINITIONS ::= BEGIN

        IMPORTS
                MODULE-IDENTITY,
                OBJECT-IDENTITY,
                OBJECT-TYPE,
                Integer32, IpAddress
                        FROM SNMPv2-SMI
                MacAddress, DateAndTime, TimeStamp, TEXTUAL-CONVENTION, TruthValue, RowStatus
                        FROM SNMPv2-TC
                softentIND1Da
                        FROM ALCATEL-IND1-BASE
                MODULE-COMPLIANCE, OBJECT-GROUP
                        FROM SNMPv2-CONF
                InterfaceIndex, InterfaceIndexOrZero
                        FROM IF-MIB
                InetAddressType, InetAddress
                        FROM INET-ADDRESS-MIB
                SnmpAdminString
                        FROM SNMP-FRAMEWORK-MIB
                        ;

        alcatelIND1DaMIB MODULE-IDENTITY
                LAST-UPDATED "201008160000Z"
                ORGANIZATION "Alcatel-Lucent"
                CONTACT-INFO
            "Please consult with Customer Service to ensure the most appropriate
             version of this document is used with the products in question:

                        Alcatel-Lucent, Enterprise Solutions Division
                       (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"

                DESCRIPTION
                        "This module describes an authoritative enterprise-specific Simple
             Network Management Protocol (SNMP) Management Information Base (MIB):

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

                REVISION      "200704030000Z"
        DESCRIPTION
            "DA module is taking care of the authentication and classification of MACs
			on a DA port. The pkts from the MAC would be allowed to enter the network
			only if the authentication and/or classification is done by the DA task."
                ::= { softentIND1Da 1}

alaIND1DaMIBObjects OBJECT-IDENTITY
        STATUS current
        DESCRIPTION
            "Branch For DA Subsystem Managed Objects."
        ::= { alcatelIND1DaMIB 1 }


    alaIND1DaMIBConformance OBJECT-IDENTITY
        STATUS current
        DESCRIPTION
            "Branch for DA Module MIB Subsystem Conformance Information."
        ::= { alcatelIND1DaMIB 2 }


    alaIND1DaMIBGroups OBJECT-IDENTITY
        STATUS current
        DESCRIPTION
            "Branch for DA Module MIB Subsystem Units of Conformance."
        ::= { alaIND1DaMIBConformance 1 }

    AlaDaClassificationPolicyType ::= TEXTUAL-CONVENTION
       STATUS       current
       DESCRIPTION
               "This policy type is the classification policy used to classify
                a device onto the system. "
       SYNTAX  INTEGER {
                authPassAltUnp ( 1 ),
                authPassDefUnp ( 2 ),
                authPassSrvUnp ( 3 ),
                noAuthMacRuleUnp ( 4 ),
                noAuthMacRangeRuleUnp ( 5 ),
                noAuthIpRuleUnp ( 6 ),
                authFailDefUnp ( 7 ),
                authFailMacRuleUnp ( 8 ),
                authFailMacRangeRuleUnp ( 9 ),
                authFailIpRuleUnp ( 10 ),
                authFailRuleDefUnp ( 11 ),
                authFailMacRangeVlanTagRuleUnp ( 12 ),
                tagAuthFailMacRuleUnp ( 13 ),
                tagAuthFailMacVlanTagRuleUnp ( 14 ),
                tagAuthFailMacRangeRuleUnp ( 15 ),
                tagAuthFailMacRangeVlanTagRuleUnp ( 16 ),
                tagAuthFailIpRuleUnp ( 17 ),
                tagAuthFailIpVlanTagRuleUnp ( 18 ),
                tagAuthFailVlanTagRuleUnp ( 19 ),
                tagAuthPassAltUnp ( 20 ),
                tagAuthPassDefUnp ( 21 ),
                tagAuthPassSrvUnp ( 22 ),
                tagMacRuleUnp ( 23 ),
                tagMacVlanTagRuleUnp ( 24 ),
                tagMacRangeRuleUnp ( 25 ),
                tagMacRangeVlanTagRuleUnp ( 26 ),
                tagIpRuleUnp ( 27 ),
                tagIpVlanTagRuleUnp ( 28 ),
                tagVlanTagRuleUnp ( 29 ),
                tagRuleDefUnp ( 30 ),
                authPassDefUnpBlk ( 31 ),
                authFailDefUnpBlk ( 32 ),
                authFailRuleDefUnpBlk ( 33 ),
                tagAuthPassDefUnpBlk ( 34 ),
                tagRuleDefUnpBlk ( 35 ),
                authPassSrvUnpTagMismatchBlk ( 36 ),
                authPassAltUnpTagMismatchBlk ( 37 ),
                authPassDefUnpTagMismatchBlk ( 38 ),
                authFailMacRuleUnpTagMismatchBlk ( 39 ),
                authFailMacVlanRuleUnpTagMismatchBlk ( 40 ),
                authFailMacRangeRuleUnpTagMismatchBlk ( 41 ),
                authFailMacRangeVlanRuleUnpTagMismatchBlk ( 42 ),
                authFailIpRuleUnpTagMismatchBlk ( 43 ),
                authFailIpVlanRuleUnpTagMismatchBlk ( 44 ),
                authFailVlanRuleUnpTagMismatchBlk ( 45 ),
                defUnpBlk ( 46 ),
                authPassSrvUnpBlk ( 47 ),
                authPassAltUnpBlk ( 48 ),
                authFailMacRuleUnpBlk ( 49 ),
                authFailMacRangeRuleUnpBlk ( 50 ),
                authFailIpRuleUnpBlk ( 51 ),
                tagMacRuleUnpBlk ( 52 ),
                tagMacVlanTagRuleUnpBlk ( 53 ),
                tagMacRangeRuleUnpBlk ( 54 ),
                tagMacRangeVlanTagRuleUnpBlk ( 55 ),
                tagIpRuleUnpBlk ( 56 ),
                tagIpVlanTagRuleUnpBlk ( 57 ),
                tagVlanTagRuleUnpBlk ( 58 ),
                authSrvDownUnpTagMismatchBlk (59),
                noMatchingUnpBlk ( 60 ),
                trustTag ( 61 ),
                authSrvDownUnp (62),
                defUnp ( 63 )
       }

       AlaDaAuthenticationType ::= TEXTUAL-CONVENTION
       STATUS       current
       DESCRIPTION
               "The type of authentication used"
       SYNTAX  INTEGER {
                   noAuthentication   (1),
                   dot1XAuthentication (2),
                   macAuthentication  (3),
                   captivePortal      (4)
       }

      AlaDaAuthenticationResult ::= TEXTUAL-CONVENTION
       STATUS       current
       DESCRIPTION
               "The result of the authentication.  If the AlaDaAuthenticationType of this
                 device is noAuthentication then this object will return notApplicable.  If the
                 authentication has not completed then this object will return inProgress."
       SYNTAX  INTEGER {
                   notApplicable (0),
                   inProgress    (1),
                   success       (2),
                   fail          (3)
       }

      AlaDaMacLearntState ::= TEXTUAL-CONVENTION
       STATUS       current
       DESCRIPTION
               "The state of MAC address in the system"
       SYNTAX  INTEGER {
                   bridging      (0), -- Normal access to the network.
                   filtering     (1) -- Access to the network blocked.
       }

--------------------------------------------------
-- User Network Profile Table configuration MIB --
--------------------------------------------------

    alaDaUserNetProfileTable OBJECT-TYPE
        SYNTAX        SEQUENCE OF AlaDaUserNetProfileEntry
        MAX-ACCESS    not-accessible
        STATUS        current
        DESCRIPTION
            "This table stores the UNP profiles created in the system.
			The entries would be mapped to vlan ID which would be used
			by device authentication for classifying users."
        ::= { alaIND1DaMIBObjects 1 }

    alaDaUserNetProfileEntry OBJECT-TYPE
        SYNTAX        AlaDaUserNetProfileEntry
        MAX-ACCESS    not-accessible
        STATUS        current
        DESCRIPTION
            "User Network Profile entry"
        INDEX {alaDaUserNetProfileName}
        ::= { alaDaUserNetProfileTable 1 }

    AlaDaUserNetProfileEntry ::= SEQUENCE
        {
            alaDaUserNetProfileName              SnmpAdminString,
            alaDaUserNetProfileVlanID            Integer32,
            alaDaUserNetProfileRowStatus         RowStatus,
            alaDaUserNetProfileQosPolicyListName SnmpAdminString
        }

    alaDaUserNetProfileName OBJECT-TYPE
        SYNTAX        SnmpAdminString ( SIZE( 1 .. 32 ) )
        MAX-ACCESS    not-accessible
        STATUS        current
        DESCRIPTION
            "The name of this profile."
        ::= { alaDaUserNetProfileEntry 1 }

    alaDaUserNetProfileVlanID OBJECT-TYPE
        SYNTAX        Integer32 (1 .. 4094)
        MAX-ACCESS    read-create
        STATUS        current
        DESCRIPTION
            "The VLAN id for this profile."
        ::= { alaDaUserNetProfileEntry 2}

    alaDaUserNetProfileRowStatus OBJECT-TYPE
        SYNTAX        RowStatus
        MAX-ACCESS    read-create
        STATUS        current
        DESCRIPTION
            "The status of this table entry."
        ::= { alaDaUserNetProfileEntry 3}

    alaDaUserNetProfileQosPolicyListName OBJECT-TYPE
        SYNTAX        SnmpAdminString ( SIZE( 0 .. 32 ) )
        MAX-ACCESS    read-create
        STATUS        current
        DESCRIPTION
            "The name of the QoS Policy List name that will be used if this
             User Network Profile is applied for a given device along with
             alaDaUserNetProfileVlanID."
        ::= { alaDaUserNetProfileEntry 4 }


------------------------------------------------
-- DA Classification IP network address rule  --
------------------------------------------------

        alaDaUNPIpNetRuleTable  OBJECT-TYPE
            SYNTAX  SEQUENCE OF AlaDaUNPIpNetRuleEntry
            MAX-ACCESS  not-accessible
            STATUS  current
            DESCRIPTION
                "A list of IP network address rules.  This is used to match
                 the InetAddress of a packet to a User Network Profile entry."
            ::= { alaIND1DaMIBObjects 2 }

        alaDaUNPIpNetRuleEntry  OBJECT-TYPE
            SYNTAX  AlaDaUNPIpNetRuleEntry
            MAX-ACCESS  not-accessible
            STATUS  current
            DESCRIPTION
                 "An IP network address rule entry."
            INDEX { alaDaUNPIpNetRuleAddrType,
                    alaDaUNPIpNetRuleAddr,
                    alaDaUNPIpNetRuleMask }
            ::= { alaDaUNPIpNetRuleTable 1 }

        AlaDaUNPIpNetRuleEntry ::= SEQUENCE {
                alaDaUNPIpNetRuleAddrType
                        InetAddressType,
                alaDaUNPIpNetRuleAddr
                        InetAddress,
                alaDaUNPIpNetRuleMask
                        InetAddress,
                alaDaUNPIpNetRuleProfileName
                        SnmpAdminString,
				alaDaUNPIpNetRuleVlanTag
						Integer32,
                alaDaUNPIpNetRuleRowStatus
                        RowStatus
                }

        alaDaUNPIpNetRuleAddrType  OBJECT-TYPE
            SYNTAX  InetAddressType
            MAX-ACCESS  not-accessible
            STATUS  current
            DESCRIPTION
                 "The IP network address type used for VLAN classification.  For now
                   Only IPv4 is supported."
            ::= { alaDaUNPIpNetRuleEntry 1 }

        alaDaUNPIpNetRuleAddr  OBJECT-TYPE
            SYNTAX  InetAddress
            MAX-ACCESS  not-accessible
            STATUS  current
            DESCRIPTION
                 "The IP network address used for VLAN classification.  Only IPv4 is
                  supported."
            ::= { alaDaUNPIpNetRuleEntry 2 }

        alaDaUNPIpNetRuleMask  OBJECT-TYPE
            SYNTAX  InetAddress
            MAX-ACCESS  not-accessible
            STATUS  current
            DESCRIPTION
                 "The IP network mask applying to the IP network address."
            ::= { alaDaUNPIpNetRuleEntry 3 }


        alaDaUNPIpNetRuleProfileName  OBJECT-TYPE
            SYNTAX  SnmpAdminString ( SIZE( 1 .. 32 ) )
            MAX-ACCESS  read-create
            STATUS  current
            DESCRIPTION
                 "The profile name in the User Network Profile Table to be
                  applied."
            ::= { alaDaUNPIpNetRuleEntry 4 }

        alaDaUNPIpNetRuleVlanTag  OBJECT-TYPE
            SYNTAX  Integer32 (0..4094)
            MAX-ACCESS  read-create
            STATUS  current
            DESCRIPTION
                 "The vlan tag to be used for classification of tagged pkts.
                  Vlan tag of 0 indicates no VLAN is associated."
            ::= { alaDaUNPIpNetRuleEntry 5 }

        alaDaUNPIpNetRuleRowStatus  OBJECT-TYPE
            SYNTAX  RowStatus
            MAX-ACCESS  read-create
            STATUS  current
            DESCRIPTION
                "Row Status for creating/deleting rules."
            ::= { alaDaUNPIpNetRuleEntry 6 }


--
-- DA Classification MAC address rule
--


        alaDaUNPMacRuleTable  OBJECT-TYPE
                SYNTAX  SEQUENCE OF AlaDaUNPMacRuleEntry
                MAX-ACCESS  not-accessible
                STATUS  current
                DESCRIPTION
                "A list of MAC address rules.  This is used to match
                 the MAC Address of a packet to a User Network Profile entry "
                ::= { alaIND1DaMIBObjects 3 }

        alaDaUNPMacRuleEntry  OBJECT-TYPE
            SYNTAX  AlaDaUNPMacRuleEntry
            MAX-ACCESS  not-accessible
            STATUS  current
            DESCRIPTION
                 "A MAC rule entry."
            INDEX {alaDaUNPMacRuleAddr }
            ::= { alaDaUNPMacRuleTable 1 }

        AlaDaUNPMacRuleEntry ::= SEQUENCE {
                alaDaUNPMacRuleAddr
                        MacAddress,
                alaDaUNPMacRuleProfileName
                        SnmpAdminString,
				alaDaUNPMacRuleVlanTag
						Integer32,
                alaDaUNPMacRuleRowStatus
                        RowStatus
                }

        alaDaUNPMacRuleAddr  OBJECT-TYPE
                SYNTAX  MacAddress
                MAX-ACCESS  not-accessible
                STATUS  current
                DESCRIPTION
                "The MAC address used for VLAN classification."
                ::= { alaDaUNPMacRuleEntry 1 }

        alaDaUNPMacRuleProfileName  OBJECT-TYPE
                SYNTAX  SnmpAdminString ( SIZE( 1 .. 32 ) )
                MAX-ACCESS  read-create
                STATUS  current
                DESCRIPTION
                 "The profile name in the User Network Profile Table to be
                  applied."
                ::= { alaDaUNPMacRuleEntry 2 }

        alaDaUNPMacRuleVlanTag  OBJECT-TYPE
            SYNTAX  Integer32 (0..4094)
            MAX-ACCESS  read-create
            STATUS  current
            DESCRIPTION
                 "The vlan tag to be used for classification of tagged pkts.
                  Vlan tag of 0 indicates no VLAN is associated."
            ::= { alaDaUNPMacRuleEntry 3 }

        alaDaUNPMacRuleRowStatus  OBJECT-TYPE
                SYNTAX  RowStatus
                MAX-ACCESS  read-create
                STATUS  current
                DESCRIPTION
                "Row Status for creating/deleting rules."
                 ::= { alaDaUNPMacRuleEntry 4 }


--
-- DA Classification MAC range rule
--

        alaDaUNPMacRangeRuleTable  OBJECT-TYPE
                SYNTAX  SEQUENCE OF AlaDaUNPMacRangeRuleEntry
                MAX-ACCESS  not-accessible
                STATUS  current
                DESCRIPTION
                "A list of MAC range rules.  This is used to match
                 the MAC Address Range of a packet to a User Network Profile entry."
                ::= { alaIND1DaMIBObjects 4 }

        alaDaUNPMacRangeRuleEntry  OBJECT-TYPE
            SYNTAX  AlaDaUNPMacRangeRuleEntry
            MAX-ACCESS  not-accessible
            STATUS  current
            DESCRIPTION
                 "A MAC range rule entry."
            INDEX {alaDaUNPMacRangeRuleLoAddr }
            ::= { alaDaUNPMacRangeRuleTable 1 }

        AlaDaUNPMacRangeRuleEntry ::= SEQUENCE {
                alaDaUNPMacRangeRuleLoAddr
                        MacAddress,
                alaDaUNPMacRangeRuleHiAddr
                        MacAddress,
                alaDaUNPMacRangeRuleProfileName
                        SnmpAdminString,
				alaDaUNPMacRangeRuleVlanTag
						Integer32,
                alaDaUNPMacRangeRuleRowStatus
                        RowStatus
                }

        alaDaUNPMacRangeRuleLoAddr  OBJECT-TYPE
                SYNTAX  MacAddress
                MAX-ACCESS  not-accessible
                STATUS  current
                DESCRIPTION
                "The lower bound of  MAC address range used for VLAN classification."
                ::= { alaDaUNPMacRangeRuleEntry 1 }

        alaDaUNPMacRangeRuleHiAddr  OBJECT-TYPE
                SYNTAX  MacAddress
                MAX-ACCESS  read-create
                STATUS  current
                DESCRIPTION
                "The upper bound of MAC address range used for VLAN classification."
                ::= { alaDaUNPMacRangeRuleEntry 2 }

        alaDaUNPMacRangeRuleProfileName  OBJECT-TYPE
                SYNTAX  SnmpAdminString ( SIZE( 1 .. 32 ) )
                MAX-ACCESS  read-create
                STATUS  current
                DESCRIPTION
                 "The profile name in the User Network Profile Table to be
                  applied."
                ::= { alaDaUNPMacRangeRuleEntry 3 }

        alaDaUNPMacRangeRuleVlanTag  OBJECT-TYPE
                SYNTAX  Integer32 (0..4094)
                MAX-ACCESS  read-create
                STATUS  current
                DESCRIPTION
                     "The vlan tag to be used for classification of tagged pkts. 
                      The range states the valid vlan range in the system. 
                      Vlan tag of 0 indicates no VLAN is associated."
                ::= { alaDaUNPMacRangeRuleEntry 4 }

        alaDaUNPMacRangeRuleRowStatus  OBJECT-TYPE
                SYNTAX  RowStatus
                MAX-ACCESS  read-create
                STATUS  current
                DESCRIPTION
                "Row Status for creating/deleting rules."
                 ::= { alaDaUNPMacRangeRuleEntry 5 }


--
-- DA Classification VLAN TAG rule
--

        alaDaUNPVlanTagRuleTable  OBJECT-TYPE
                SYNTAX  SEQUENCE OF AlaDaUNPVlanTagRuleEntry
                MAX-ACCESS  not-accessible
                STATUS  current
                DESCRIPTION
                "A list of Vlan Tag based classification rules.  This is used to match
                 the vlan tag in a packet to a User Network Profile entry "
                ::= { alaIND1DaMIBObjects 5 }

        alaDaUNPVlanTagRuleEntry  OBJECT-TYPE
            SYNTAX  AlaDaUNPVlanTagRuleEntry
            MAX-ACCESS  not-accessible
            STATUS  current
            DESCRIPTION
                 "A Vlan Tag rule entry."
            INDEX {alaDaUNPVlanTagRuleVlan }
            ::= { alaDaUNPVlanTagRuleTable 1 }

        AlaDaUNPVlanTagRuleEntry ::= SEQUENCE {
                alaDaUNPVlanTagRuleVlan
						Integer32,
                alaDaUNPVlanTagRuleProfileName
                        SnmpAdminString,
                alaDaUNPVlanTagRuleRowStatus
                        RowStatus
                }

        alaDaUNPVlanTagRuleVlan  OBJECT-TYPE
                SYNTAX  Integer32 (1..4094)
                MAX-ACCESS  not-accessible
                STATUS  current
                DESCRIPTION
                "The Vlan Tag used for VLAN classification. The range states the valid
				 Vlan range in the system."
                ::= { alaDaUNPVlanTagRuleEntry 1 }

        alaDaUNPVlanTagRuleProfileName  OBJECT-TYPE
                SYNTAX  SnmpAdminString ( SIZE( 1 .. 32 ) )
                MAX-ACCESS  read-create
                STATUS  current
                DESCRIPTION
                 "The profile name in the User Network Profile Table to be
                  applied."
                ::= { alaDaUNPVlanTagRuleEntry 2 }

        alaDaUNPVlanTagRuleRowStatus  OBJECT-TYPE
                SYNTAX  RowStatus
                MAX-ACCESS  read-create
                STATUS  current
                DESCRIPTION
                "Row Status for creating/deleting rules."
                 ::= { alaDaUNPVlanTagRuleEntry 3 }

--
-- DA MAC User Table
--

alaDaMacUserTable OBJECT-TYPE
        SYNTAX      SEQUENCE OF AlaDaMacUserEntry
        MAX-ACCESS  not-accessible
        STATUS      current
        DESCRIPTION
        "A table of non 802.1x supplicants learned on 802.1x authenticated ports."
::= { alaIND1DaMIBObjects 6 }

alaDaMacUserEntry OBJECT-TYPE
        SYNTAX      AlaDaMacUserEntry
        MAX-ACCESS  not-accessible
        STATUS      current
        DESCRIPTION
                "Non 802.1x supplicant information."
        INDEX { alaDaMacUserIntfNum,
                alaDaMacUserMACAddress }
::= { alaDaMacUserTable 1 }


AlaDaMacUserEntry ::=
        SEQUENCE {
                alaDaMacUserIntfNum
                    InterfaceIndex,
                alaDaMacUserMACAddress 
					MacAddress,
                alaDaMacUserVlanID     
					Integer32,
                alaDaAuthenticationStatus    
					INTEGER,
				alaDaMacUserIpAddress     
					IpAddress,
				alaDaMacUserUnpUsed    
					SnmpAdminString,
				alaDaMacUserLoginTimeStamp
					DateAndTime,
				alaDaMacUserAuthtype
					INTEGER,
				alaDaMacUserClassificationSource
					AlaDaClassificationPolicyType
                }

alaDaMacUserIntfNum OBJECT-TYPE
    SYNTAX      InterfaceIndex
    MAX-ACCESS  not-accessible
    STATUS      current
    DESCRIPTION
        "The ifIndex representing the slot and port where the non 802.1x supplicant is learned."
    ::= { alaDaMacUserEntry 1 }

alaDaMacUserMACAddress OBJECT-TYPE
    SYNTAX      MacAddress
    MAX-ACCESS  not-accessible
    STATUS      current
    DESCRIPTION
        "The MAC address of the non 802.1x supplicant."
    ::= { alaDaMacUserEntry 2 }

alaDaMacUserVlanID OBJECT-TYPE
        SYNTAX      Integer32 (1..4096)
        MAX-ACCESS  read-only
        STATUS      current
        DESCRIPTION
        "The Id of the VLAN on which the non 802.1x supplicant is learned."
    ::= { alaDaMacUserEntry 3 }

alaDaAuthenticationStatus  OBJECT-TYPE
        SYNTAX  INTEGER {
                idle (1),
                inProgress (2),
                authenticated (3),
                failed (4),
                failedTimeout (5),
                failedNoServer (6),
                failedNoResources (7)
            }

        MAX-ACCESS  read-only
        STATUS      current
        DESCRIPTION
        "Authentication status of the non 802.1x supplicant."
    ::= { alaDaMacUserEntry 4 }

alaDaMacUserIpAddress OBJECT-TYPE
    SYNTAX      IpAddress
    MAX-ACCESS  read-only
    STATUS      current
    DESCRIPTION
        "The ip address from which the mac user is sending the packets"
    ::= { alaDaMacUserEntry 5 }

alaDaMacUserUnpUsed OBJECT-TYPE
    SYNTAX      SnmpAdminString
    MAX-ACCESS  read-only
    STATUS      current
    DESCRIPTION
        "The UNP used for classifying the mac user"
    ::= { alaDaMacUserEntry 6 }

alaDaMacUserLoginTimeStamp OBJECT-TYPE
    SYNTAX      DateAndTime
    MAX-ACCESS  read-only
    STATUS      current
    DESCRIPTION
        "The Login time stamp of the mac user"
    ::= { alaDaMacUserEntry 7 }

alaDaMacUserAuthtype OBJECT-TYPE
    SYNTAX      INTEGER {
		macAuthentication	(0),
		others (1)
	}
    MAX-ACCESS  read-only
    STATUS      current
    DESCRIPTION
        "The authentication type of the mac user"
    ::= { alaDaMacUserEntry 8 }

alaDaMacUserClassificationSource OBJECT-TYPE
        SYNTAX      AlaDaClassificationPolicyType
        MAX-ACCESS  read-only
        STATUS      current
        DESCRIPTION
        "Classification policy under which the non 802.1x supplicant is learned."
    ::= { alaDaMacUserEntry 9 }
--
-- Logical Port table
--

alaDaUNPPortTable OBJECT-TYPE
    SYNTAX      SEQUENCE OF AlaDaUNPPortEntry
    MAX-ACCESS  not-accessible
    STATUS      current
    DESCRIPTION
        "A table of system level information for each port
        supported by the Port Access Entity.  An entry appears
        in this table for each port of this system."
    REFERENCE
        "9.6.1"
    ::= { alaIND1DaMIBObjects 7 }

alaDaUNPPortEntry OBJECT-TYPE
    SYNTAX      AlaDaUNPPortEntry
    MAX-ACCESS  not-accessible
    STATUS      current
    DESCRIPTION
        "Each of these entries represents a user port on which UNP is enabled and their
		 configuration."
    INDEX { alaDaUNPPortIfIndex }
    ::= { alaDaUNPPortTable 1 }


AlaDaUNPPortEntry ::=
    SEQUENCE {
		alaDaUNPPortIfIndex
			InterfaceIndexOrZero,
        alaDaUNPPortDefaultProfileName
            SnmpAdminString,
        alaDaUNPPortPassAltProfileName
            SnmpAdminString,
        alaDaUNPPortRowStatus
            RowStatus,
        alaDaUNPPortMacAuthFlag
            INTEGER,
        alaDaUNPPortClassificationFlag
            INTEGER,
        alaDaUNPPortTrustTagStatus
            INTEGER
        }

alaDaUNPPortIfIndex OBJECT-TYPE
    SYNTAX      InterfaceIndexOrZero
    MAX-ACCESS  not-accessible
    STATUS      current
    DESCRIPTION
        "The interface index of the UNP enabled port"
    ::= { alaDaUNPPortEntry 1 }

alaDaUNPPortDefaultProfileName OBJECT-TYPE
    SYNTAX      SnmpAdminString ( SIZE( 0 .. 32 ) )
    MAX-ACCESS  read-create
    STATUS      current
    DESCRIPTION
        "The default UNP name."
    ::= { alaDaUNPPortEntry 2 }

alaDaUNPPortPassAltProfileName OBJECT-TYPE
    SYNTAX      SnmpAdminString ( SIZE( 0 .. 32 ) )
    MAX-ACCESS  read-create
    STATUS      current
    DESCRIPTION
        "The Pass alternate UNP name."
    ::= { alaDaUNPPortEntry 3 }

alaDaUNPPortRowStatus OBJECT-TYPE
    SYNTAX      RowStatus
    MAX-ACCESS  read-create
    STATUS      current
    DESCRIPTION
        "The status of this table entry."
    ::= { alaDaUNPPortEntry 4 }

alaDaUNPPortMacAuthFlag OBJECT-TYPE
    SYNTAX      INTEGER {
		enable  (1),
		disable (2)
	}
    MAX-ACCESS  read-create
    STATUS      current
    DESCRIPTION
        "The flag to indicate if MAC AUTH is enabled on port."
    ::= { alaDaUNPPortEntry 5 }

alaDaUNPPortClassificationFlag OBJECT-TYPE
    SYNTAX      INTEGER {
		enable  (1),
		disable (2)
	}
    MAX-ACCESS  read-create
    STATUS      current
    DESCRIPTION
        "The flag to indicate if Classification is enabled on port."
    ::= { alaDaUNPPortEntry 6 }

alaDaUNPPortTrustTagStatus OBJECT-TYPE
    SYNTAX      INTEGER {
		enable  (1),
		disable (2)
	}
    MAX-ACCESS  read-create
    STATUS      current
    DESCRIPTION
        "The flag to indicate whether the vlan tag in the incoming packet
		could be used for classifying the user when mac authentication fails 
		and classification rules dont match."
    ::= { alaDaUNPPortEntry 7 }


--
--  UNP Global configuration
--

    alaDaUNPGlobalConfiguration    OBJECT IDENTIFIER ::= { alaIND1DaMIBObjects 8 }

    alaDaUNPDynamicVlanConfigFlag OBJECT-TYPE
    SYNTAX      INTEGER {
                enable  (1),
                disable (2)
        }
    MAX-ACCESS  read-write
    STATUS      current
    DESCRIPTION
        "Indicated whether dynamic vlan configuration is enabled or not."
	DEFVAL      { disable }
    ::= { alaDaUNPGlobalConfiguration 1 }

    alaDaUNPAuthServerDownUnp OBJECT-TYPE
    SYNTAX      SnmpAdminString (SIZE(0..32))
    MAX-ACCESS  read-write
    STATUS      current
    DESCRIPTION
	"The UNP to be used for classification if the authentication server 
	is not reachable."
    ::= { alaDaUNPGlobalConfiguration 2 }

    alaDaUNPAuthServerDownTimeout OBJECT-TYPE
    SYNTAX      Integer32 (10..1000)
    UNITS       "Seconds"
    MAX-ACCESS  read-write
    STATUS      current
    DESCRIPTION
	"The timeout, in seconds, after which all the users learned in the auth-server-down
	UNP will be sent for re-authentication."
	DEFVAL      { 60 }
    ::= { alaDaUNPGlobalConfiguration 3 }

--
-- MIB compliance
--

    alaIND1DaMIBCompliances MODULE-COMPLIANCE
        STATUS  current
        DESCRIPTION
            "Compliance statement for Alcatel DA module."
        MODULE
            MANDATORY-GROUPS
            {
			alaDaUserNetProfileGroup,
			alaDaUNPIpNetRuleGroup,
			alaDaUNPMacRuleGroup,
			alaDaUNPMacRangeGroup,
			alaDaUNPVlanTagGroup,
			alaDaMacUserGroup,
			alaDaUNPPortGroup,
            alaDaUNPGlobalGroup
			}
        ::= { alaIND1DaMIBConformance 2 }
	

--
-- Units of Conformance
--

    alaDaUserNetProfileGroup OBJECT-GROUP
        OBJECTS
        {
            alaDaUserNetProfileVlanID,
            alaDaUserNetProfileRowStatus,
            alaDaUserNetProfileQosPolicyListName
        }
        STATUS  current
        DESCRIPTION
            "Collection of DA objects for UNP Table"
        ::= { alaIND1DaMIBGroups 1 }

    alaDaUNPIpNetRuleGroup OBJECT-GROUP
        OBJECTS
        {
            alaDaUNPIpNetRuleProfileName ,
	    alaDaUNPIpNetRuleVlanTag ,
	    alaDaUNPIpNetRuleRowStatus
        }
        STATUS  current
        DESCRIPTION
            "Collection of DA objects for UNP Ip rule"
        ::= { alaIND1DaMIBGroups 2 }

    alaDaUNPMacRuleGroup OBJECT-GROUP
        OBJECTS
        {
            alaDaUNPMacRuleProfileName ,
	    alaDaUNPMacRuleVlanTag ,
            alaDaUNPMacRuleRowStatus
        }
        STATUS  current
        DESCRIPTION
            "Collection of DA objects for UNP Mac Rule"
        ::= { alaIND1DaMIBGroups 3 }

    alaDaUNPMacRangeGroup OBJECT-GROUP
        OBJECTS
        {
            alaDaUNPMacRangeRuleHiAddr ,
            alaDaUNPMacRangeRuleProfileName ,
	    alaDaUNPMacRangeRuleVlanTag ,
            alaDaUNPMacRangeRuleRowStatus
        }
        STATUS  current
        DESCRIPTION
            "Collection of DA objects for UNP Mac Rangel Rule"
        ::= { alaIND1DaMIBGroups 4 }

    alaDaUNPVlanTagGroup OBJECT-GROUP
        OBJECTS
        {
	    alaDaUNPVlanTagRuleProfileName ,
            alaDaUNPVlanTagRuleRowStatus
        }
        STATUS  current
        DESCRIPTION
            "Collection of DA objects for Vlan Tag Rule"
        ::= { alaIND1DaMIBGroups 5 }

    alaDaMacUserGroup OBJECT-GROUP
        OBJECTS
        {
            alaDaMacUserVlanID,
            alaDaAuthenticationStatus,
			alaDaMacUserIpAddress,
			alaDaMacUserUnpUsed,
			alaDaMacUserLoginTimeStamp,
			alaDaMacUserAuthtype,
			alaDaMacUserClassificationSource
        }
        STATUS  current
        DESCRIPTION
            "Collection of DA objects for UNP Mac User"
        ::= { alaIND1DaMIBGroups 6 }

    alaDaUNPPortGroup OBJECT-GROUP
        OBJECTS
        {
        alaDaUNPPortDefaultProfileName,
        alaDaUNPPortPassAltProfileName,
        alaDaUNPPortRowStatus,
        alaDaUNPPortMacAuthFlag,
        alaDaUNPPortClassificationFlag,
		alaDaUNPPortTrustTagStatus
        }
        STATUS  current
        DESCRIPTION
            "Collection of DA UNP Ports"
        ::= { alaIND1DaMIBGroups 7 }

    alaDaUNPGlobalGroup OBJECT-GROUP
        OBJECTS
        {
        alaDaUNPDynamicVlanConfigFlag,
        alaDaUNPAuthServerDownUnp,
        alaDaUNPAuthServerDownTimeout
        }
        STATUS  current
        DESCRIPTION
            "Collection of DA objects for Global parameters"
        ::= { alaIND1DaMIBGroups 8 }

END
