ALCATEL-IND1-QOS-MIB DEFINITIONS ::= BEGIN

IMPORTS
  OBJECT-TYPE, OBJECT-IDENTITY, MODULE-IDENTITY,
  Counter32, Counter64, Integer32, IpAddress
    FROM SNMPv2-SMI
  OBJECT-GROUP, MODULE-COMPLIANCE
    FROM SNMPv2-CONF
  MacAddress, RowStatus
    FROM SNMPv2-TC
  SnmpAdminString
    FROM SNMP-FRAMEWORK-MIB
  softentIND1QoS
    FROM ALCATEL-IND1-BASE
  Ipv6Address
    FROM IPV6-TC;


alaQoSMIB MODULE-IDENTITY
  LAST-UPDATED "200704030000Z"
  ORGANIZATION "Alcatel IND"
  CONTACT-INFO
    "David Morgan
    E-Mail: David.Morgan@ind.alcatel.com"
  DESCRIPTION
    "QoS and Filtering MIB"
  ::= { softentIND1QoS 1 }

-- FILE: ALCATEL-IND1-QOS-MIB.mib

-- Alcatel
-- Architects Of An Internet World

-- This module provides authoritative enterprise-specific Simple Network
-- Management Protocol (SNMP) Management Information Base (MIB) definitions.

-- The right to make changes in specification and other information contained
-- in this document without prior notice is reserved.

-- No liability shall be assumed for any incidental, indirect, special, or
-- consequential damages whatsoever arising from or related to this document or
-- the information contained herein.

-- Vendors, end-users, and other interested parties are granted non-exclusive
-- license to use this specification in connection with management of the
-- products for which it is intended to be used.

-- Please consult with Customer Service to ensure the most appropriate version
-- of this document is used with the products in question:

-- Alcatel-Lucent, Enterprise Solutions Division
-- (Formerly Alcatel Internetworking, Incorporated)
-- 26801 West Agoura Road
-- Calabasas, CA 91301
-- United States Of America

-- Telephone: North America 800.995.2696
-- Latin America 877.919.9526
-- Europe 31.23.556.0100
-- Asia 65.394.7933
-- All Other 818.878.4507

-- Electronic Mail: support@ind.alcatel.com
-- World Wide Web: http://alcatel-lucent.com/wps/portal/enterprise
-- File Transfer Protocol: ftp://ftp.ind.alcatel.com/pub/products/mibs

-- Copyright (C) 1995-2007 Alcatel-Lucent
-- ALL RIGHTS RESERVED WORLDWIDE


alaQoSMIBObjects OBJECT-IDENTITY
  STATUS      current
  DESCRIPTION "Branch for QoS Managed Objects."
  ::= { alaQoSMIB 1 }


--
-- Definition of rule table
--

alaQoSRuleTable OBJECT-TYPE
  SYNTAX      SEQUENCE OF QoSRuleEntry
  MAX-ACCESS  not-accessible
  STATUS      current
  DESCRIPTION "Table of QoS Rule definitions"
  ::= { alaQoSMIBObjects 1 }

alaQoSRuleEntry OBJECT-TYPE
  SYNTAX      QoSRuleEntry
  MAX-ACCESS  not-accessible
  STATUS      current
  DESCRIPTION "Definition of QoS Rule"
  INDEX {
          alaQoSRuleName
        }
  ::= { alaQoSRuleTable 1 }

QoSRuleEntry ::=
  SEQUENCE
  {
    alaQoSRuleName                                          SnmpAdminString,
    alaQoSRuleEnabled                                       INTEGER,
    alaQoSRuleSource                                        INTEGER,
    alaQoSRulePrecedence                                    Integer32,
    alaQoSRuleCondition                                     SnmpAdminString,
    alaQoSRuleAction                                        SnmpAdminString,
    alaQoSRuleReflexive                                     INTEGER,
    alaQoSRuleSave                                          INTEGER,
    alaQoSRuleLog                                           INTEGER,
    alaQoSRuleEnforced                                      INTEGER,
    alaQoSRuleActive                                        INTEGER,
    alaQoSRuleRowStatus                                     RowStatus,
    alaQoSRuleValidityPeriod                                SnmpAdminString,
    alaQoSRuleValidityPeriodStatus                          INTEGER,
    alaQoSRuleLogInterval                                   Integer32,
    alaQoSRuleCountType                                     INTEGER,
    alaQoSRulePacketCount                                   Counter64,
    alaQoSRuleByteCount                                     Counter64,
    alaQoSRuleType                                          Integer32,
    alaQoSRuleTrapEvents                                    INTEGER,
    alaQoSRuleDefaultList                                   INTEGER,
    alaQoSRuleGreenPacketCount                              Counter64,
    alaQoSRuleYellowPacketCount                             Counter64,
    alaQoSRuleRedPacketCount                                Counter64,
    alaQoSRuleGreenByteCount                                Counter64,
    alaQoSRuleYellowByteCount                               Counter64,
    alaQoSRuleRedByteCount                                  Counter64
  }

alaQoSRuleName OBJECT-TYPE
  SYNTAX      SnmpAdminString (SIZE(0..31))
  MAX-ACCESS  not-accessible
  STATUS      current
  DESCRIPTION "Name of rule"
  ::= { alaQoSRuleEntry 1 }

alaQoSRuleEnabled OBJECT-TYPE
  SYNTAX      INTEGER {
                enable (1),
                disable (2)
              }
  MAX-ACCESS  read-create
  STATUS      current
  DESCRIPTION "Is this rule enabled or not"
  DEFVAL      { enable }
  ::= { alaQoSRuleEntry 2 }

alaQoSRuleSource OBJECT-TYPE
  SYNTAX      INTEGER {
                ldap (1),
                cli (2),
                blt (3),
                api (4),
                imp (5)
              }
  MAX-ACCESS  read-create
  STATUS      current
  DESCRIPTION "What entity created the rule."
  DEFVAL      { cli }
  ::= { alaQoSRuleEntry 3 }

alaQoSRulePrecedence OBJECT-TYPE
  SYNTAX      Integer32 (0..65535)
  MAX-ACCESS  read-create
  STATUS      current
  DESCRIPTION "Precedence value for rule.
               Rules are evaluated from higher precedence to lower.
               If rules have equal precedence, they are evaluated in
               the order they are received."
  DEFVAL      { 0 }
  ::= { alaQoSRuleEntry 4 }

alaQoSRuleCondition OBJECT-TYPE
  SYNTAX      SnmpAdminString (SIZE(0..31))
  MAX-ACCESS  read-create
  STATUS      current
  DESCRIPTION "Name of the condition to use"
  ::= { alaQoSRuleEntry 5 }

alaQoSRuleAction OBJECT-TYPE
  SYNTAX      SnmpAdminString (SIZE(0..31))
  MAX-ACCESS  read-create
  STATUS      current
  DESCRIPTION "Name of the action to use"
  ::= { alaQoSRuleEntry 6 }

alaQoSRuleReflexive OBJECT-TYPE
  SYNTAX      INTEGER {
                yes (1),
                no (2)
              }
  MAX-ACCESS  read-create
  STATUS      current
  DESCRIPTION "Indicator to tell if the rule is reflexive.  Reflexive rules
               allow specific return connections that would normally be denied."
  DEFVAL      { no }
  ::= { alaQoSRuleEntry 7 }

alaQoSRuleSave OBJECT-TYPE
  SYNTAX      INTEGER {
                yes (1),
                no (2)
              }
  MAX-ACCESS  read-create
  STATUS      current
  DESCRIPTION "Indicator to tell whether to write out the rule during
               snapshot commands."
  DEFVAL      { yes }
  ::= { alaQoSRuleEntry 8 }

alaQoSRuleLog OBJECT-TYPE
  SYNTAX      INTEGER {
                yes (1),
                no (2)
              }
  MAX-ACCESS  read-create
  STATUS      current
  DESCRIPTION "Indicator to tell whether to log matches to this rule
               in the QoS log."
  DEFVAL      { no }
  ::= { alaQoSRuleEntry 9 }

alaQoSRuleEnforced OBJECT-TYPE
  SYNTAX      INTEGER {
                yes (1),
                no (2)
              }
  MAX-ACCESS  read-only
  STATUS      current
  DESCRIPTION "Is this rule currenly being enforced on the switch."
  ::= { alaQoSRuleEntry 10 }

alaQoSRuleActive OBJECT-TYPE
  SYNTAX      INTEGER {
                yes (1),
                no (2)
              }
  MAX-ACCESS  read-only
  STATUS      current
  DESCRIPTION "Is this rule enforcable by the switch."
  ::= { alaQoSRuleEntry 11 }

alaQoSRuleRowStatus OBJECT-TYPE
  SYNTAX      RowStatus
  MAX-ACCESS  read-create
  STATUS      current
  DESCRIPTION "Used to create/delete rules according to the
               RowStatus convention"
  ::= { alaQoSRuleEntry 12 }

alaQoSRuleValidityPeriod OBJECT-TYPE
  SYNTAX      SnmpAdminString (SIZE(0..31))
  MAX-ACCESS  read-create
  STATUS      current
  DESCRIPTION "Name of the validity period to use"
  ::= { alaQoSRuleEntry 13 }

alaQoSRuleValidityPeriodStatus OBJECT-TYPE
  SYNTAX      INTEGER {
                enabled (1),
                disabled (2)
              }
  MAX-ACCESS  read-create
  STATUS      current
  DESCRIPTION "Status field indicating whether there is a validity period
               associated with this rule"
  DEFVAL      { disabled }
  ::= { alaQoSRuleEntry 14 }

alaQoSRuleLogInterval OBJECT-TYPE
  SYNTAX      Integer32 (0..3600)
  MAX-ACCESS  read-create
  STATUS      current
  DESCRIPTION "How often to look for packets matching this rule when logging.
               When 0 log as many as possible."
  DEFVAL      { 30 }
  ::= { alaQoSRuleEntry 15 }

alaQoSRuleCountType OBJECT-TYPE
  SYNTAX      INTEGER {
                packets (1),
                bytes (2)
              }
  MAX-ACCESS  read-create
  STATUS      current
  DESCRIPTION "Which rule statistics counters to update if not all are available"
  DEFVAL      { packets }
  ::= { alaQoSRuleEntry 16 }

alaQoSRulePacketCount OBJECT-TYPE
  SYNTAX      Counter64
  MAX-ACCESS  read-only
  STATUS      current
  DESCRIPTION "Counter for packets patching this rule"
  ::= { alaQoSRuleEntry 17 }

alaQoSRuleByteCount OBJECT-TYPE
  SYNTAX      Counter64
  MAX-ACCESS  read-only
  STATUS      current
  DESCRIPTION "Counter for bytes matching this rule"
  ::= { alaQoSRuleEntry 18 }

alaQoSRuleType OBJECT-TYPE
  SYNTAX      Integer32
  MAX-ACCESS  read-only
  STATUS      current
  DESCRIPTION "The type of rule this is. Each bit represents the following:
               0x1 = bridged
               0x2 = routed
               0x4 = multicast"
  ::= { alaQoSRuleEntry 19 }

alaQoSRuleTrapEvents OBJECT-TYPE
  SYNTAX      INTEGER {
                yes (1),
                no (2)
              }
  MAX-ACCESS  read-create
  STATUS      current
  DESCRIPTION "Send SNMP trap when 'qos user-port shutdown' param or
                rule having action=port-disable is matched/invoked?"
  DEFVAL      { yes }
  ::= { alaQoSRuleEntry 20 }

alaQoSRuleDefaultList OBJECT-TYPE
  SYNTAX      INTEGER {
                yes (1),
                no (2)
              }
  MAX-ACCESS  read-create
  STATUS      current
  DESCRIPTION "This rule belongs to the default policy list. "
  DEFVAL      { yes }
  ::= { alaQoSRuleEntry 21 }

alaQoSRuleGreenPacketCount  OBJECT-TYPE
  SYNTAX      Counter64
  MAX-ACCESS  read-only
  STATUS      current
  DESCRIPTION "Counter for the number of  packets being green compliant."
  ::= { alaQoSRuleEntry 22 }

alaQoSRuleYellowPacketCount  OBJECT-TYPE
  SYNTAX      Counter64
  MAX-ACCESS  read-only
  STATUS      current
  DESCRIPTION "Counter for the number of packets being yellow compliant."
  ::= { alaQoSRuleEntry 23 }

alaQoSRuleRedPacketCount  OBJECT-TYPE
  SYNTAX      Counter64
  MAX-ACCESS  read-only
  STATUS      current
  DESCRIPTION "Counter for the number of packets being red compliant."
  ::= { alaQoSRuleEntry 24 }

alaQoSRuleGreenByteCount  OBJECT-TYPE
  SYNTAX      Counter64
  MAX-ACCESS  read-only
  STATUS      current
  DESCRIPTION "Counter for the number of  packets being green compliant."
  ::= { alaQoSRuleEntry 25 }

alaQoSRuleYellowByteCount  OBJECT-TYPE
  SYNTAX      Counter64
  MAX-ACCESS  read-only
  STATUS      current
  DESCRIPTION "Counter for the number of packets being yellow compliant."
  ::= { alaQoSRuleEntry 26 }

alaQoSRuleRedByteCount  OBJECT-TYPE
  SYNTAX      Counter64
  MAX-ACCESS  read-only
  STATUS      current
  DESCRIPTION "Counter for the number of packets being red compliant."
  ::= { alaQoSRuleEntry 27 }

--
-- Definition of rule table
--

alaQoSAppliedRuleTable OBJECT-TYPE
  SYNTAX      SEQUENCE OF QoSAppliedRuleEntry
  MAX-ACCESS  not-accessible
  STATUS      current
  DESCRIPTION "Table of QoS AppliedRule definitions"
  ::= { alaQoSMIBObjects 2 }

alaQoSAppliedRuleEntry OBJECT-TYPE
  SYNTAX      QoSAppliedRuleEntry
  MAX-ACCESS  not-accessible
  STATUS      current
  DESCRIPTION "Definition of QoS AppliedRule"
  INDEX {
          alaQoSAppliedRuleName
        }
  ::= { alaQoSAppliedRuleTable 1 }

QoSAppliedRuleEntry ::=
  SEQUENCE
  {
    alaQoSAppliedRuleName                                   SnmpAdminString,
    alaQoSAppliedRuleEnabled                                INTEGER,
    alaQoSAppliedRuleSource                                 INTEGER,
    alaQoSAppliedRulePrecedence                             Integer32,
    alaQoSAppliedRuleCondition                              SnmpAdminString,
    alaQoSAppliedRuleAction                                 SnmpAdminString,
    alaQoSAppliedRuleReflexive                              INTEGER,
    alaQoSAppliedRuleSave                                   INTEGER,
    alaQoSAppliedRuleLog                                    INTEGER,
    alaQoSAppliedRuleEnforced                               INTEGER,
    alaQoSAppliedRuleActive                                 INTEGER,
    alaQoSAppliedRuleRowStatus                              RowStatus,
    alaQoSAppliedRuleValidityPeriod                         SnmpAdminString,
    alaQoSAppliedRuleValidityPeriodStatus                   INTEGER,
    alaQoSAppliedRuleLogInterval                            Integer32,
    alaQoSAppliedRuleCountType                              INTEGER,
    alaQoSAppliedRulePacketCount                            Counter64,
    alaQoSAppliedRuleByteCount                              Counter64,
    alaQoSAppliedRuleType                                   Integer32,
    alaQoSAppliedRuleTrapEvents                             INTEGER,
    alaQoSAppliedRuleDefaultList                            INTEGER,
    alaQoSAppliedRuleGreenPacketCount                       Counter64,
    alaQoSAppliedRuleYellowPacketCount                      Counter64,
    alaQoSAppliedRuleRedPacketCount                         Counter64,
    alaQoSAppliedRuleGreenByteCount                         Counter64,
    alaQoSAppliedRuleYellowByteCount                        Counter64,
    alaQoSAppliedRuleRedByteCount                           Counter64
  }

alaQoSAppliedRuleName OBJECT-TYPE
  SYNTAX      SnmpAdminString (SIZE(0..31))
  MAX-ACCESS  not-accessible
  STATUS      current
  DESCRIPTION "Name of rule"
  ::= { alaQoSAppliedRuleEntry 1 }

alaQoSAppliedRuleEnabled OBJECT-TYPE
  SYNTAX      INTEGER {
                enable (1),
                disable (2)
              }
  MAX-ACCESS  read-only
  STATUS      current
  DESCRIPTION "Is this rule enabled or not"
  ::= { alaQoSAppliedRuleEntry 2 }

alaQoSAppliedRuleSource OBJECT-TYPE
  SYNTAX      INTEGER {
                ldap (1),
                cli (2),
                blt (3),
                api (4),
                imp (5)
              }
  MAX-ACCESS  read-only
  STATUS      current
  DESCRIPTION "What entity created the rule."
  ::= { alaQoSAppliedRuleEntry 3 }

alaQoSAppliedRulePrecedence OBJECT-TYPE
  SYNTAX      Integer32 (0..65535)
  MAX-ACCESS  read-only
  STATUS      current
  DESCRIPTION "Precedence value for rule.
               Rules are evaluated from higher precedence to lower.
               If rules have equal precedence, they are evaluated in
               the order they are received."
  ::= { alaQoSAppliedRuleEntry 4 }

alaQoSAppliedRuleCondition OBJECT-TYPE
  SYNTAX      SnmpAdminString (SIZE(0..31))
  MAX-ACCESS  read-only
  STATUS      current
  DESCRIPTION "Name of the condition to use"
  ::= { alaQoSAppliedRuleEntry 5 }

alaQoSAppliedRuleAction OBJECT-TYPE
  SYNTAX      SnmpAdminString (SIZE(0..31))
  MAX-ACCESS  read-only
  STATUS      current
  DESCRIPTION "Name of the action to use"
  ::= { alaQoSAppliedRuleEntry 6 }

alaQoSAppliedRuleReflexive OBJECT-TYPE
  SYNTAX      INTEGER {
                yes (1),
                no (2)
              }
  MAX-ACCESS  read-only
  STATUS      current
  DESCRIPTION "Indicator to tell if the rule is reflexive.  Reflexive rules
               allow specific return connections that would normally be denied."
  ::= { alaQoSAppliedRuleEntry 7 }

alaQoSAppliedRuleSave OBJECT-TYPE
  SYNTAX      INTEGER {
                yes (1),
                no (2)
              }
  MAX-ACCESS  read-only
  STATUS      current
  DESCRIPTION "Indicator to tell whether to write out the rule during
               snapshot commands."
  ::= { alaQoSAppliedRuleEntry 8 }

alaQoSAppliedRuleLog OBJECT-TYPE
  SYNTAX      INTEGER {
                yes (1),
                no (2)
              }
  MAX-ACCESS  read-only
  STATUS      current
  DESCRIPTION "Indicator to tell whether to log matches to this rule
               in the QoS log."
  ::= { alaQoSAppliedRuleEntry 9 }

alaQoSAppliedRuleEnforced OBJECT-TYPE
  SYNTAX      INTEGER {
                yes (1),
                no (2)
              }
  MAX-ACCESS  read-only
  STATUS      current
  DESCRIPTION "Is this rule currenly being enforced on the switch."
  ::= { alaQoSAppliedRuleEntry 10 }

alaQoSAppliedRuleActive OBJECT-TYPE
  SYNTAX      INTEGER {
                yes (1),
                no (2)
              }
  MAX-ACCESS  read-only
  STATUS      current
  DESCRIPTION "Is this rule enforcable by the switch."
  ::= { alaQoSAppliedRuleEntry 11 }

alaQoSAppliedRuleRowStatus OBJECT-TYPE
  SYNTAX      RowStatus
  MAX-ACCESS  read-only
  STATUS      current
  DESCRIPTION "Used to create/delete rules according to the
               RowStatus convention"
  ::= { alaQoSAppliedRuleEntry 12 }

alaQoSAppliedRuleValidityPeriod OBJECT-TYPE
  SYNTAX      SnmpAdminString (SIZE(0..31))
  MAX-ACCESS  read-only
  STATUS      current
  DESCRIPTION "Name of the validity period to use"
  ::= { alaQoSAppliedRuleEntry 13 }

alaQoSAppliedRuleValidityPeriodStatus OBJECT-TYPE
  SYNTAX      INTEGER {
                enabled (1),
                disabled (2)
              }
  MAX-ACCESS  read-only
  STATUS      current
  DESCRIPTION "Status field indicating whether there is a validity period
               associated with this rule"
  ::= { alaQoSAppliedRuleEntry 14 }

alaQoSAppliedRuleLogInterval OBJECT-TYPE
  SYNTAX      Integer32 (0..3600)
  MAX-ACCESS  read-only
  STATUS      current
  DESCRIPTION "How often to look for packets matching this rule when logging.
               When 0 log as many as possible."
  ::= { alaQoSAppliedRuleEntry 15 }

alaQoSAppliedRuleCountType OBJECT-TYPE
  SYNTAX      INTEGER {
                packets (1),
                bytes (2)
              }
  MAX-ACCESS  read-only
  STATUS      current
  DESCRIPTION "Which rule statistics counters to update if not all are available"
  ::= { alaQoSAppliedRuleEntry 16 }

alaQoSAppliedRulePacketCount OBJECT-TYPE
  SYNTAX      Counter64
  MAX-ACCESS  read-only
  STATUS      current
  DESCRIPTION "Counter for packets patching this rule"
  ::= { alaQoSAppliedRuleEntry 17 }

alaQoSAppliedRuleByteCount OBJECT-TYPE
  SYNTAX      Counter64
  MAX-ACCESS  read-only
  STATUS      current
  DESCRIPTION "Counter for bytes matching this rule"
  ::= { alaQoSAppliedRuleEntry 18 }


alaQoSAppliedRuleType OBJECT-TYPE
  SYNTAX      Integer32
  MAX-ACCESS  read-only
  STATUS      current
  DESCRIPTION "The type of rule this is. Each bit represents the following:
               0x1 = bridged
               0x2 = routed
               0x4 = multicast"
  ::= { alaQoSAppliedRuleEntry 19 }

alaQoSAppliedRuleTrapEvents OBJECT-TYPE
  SYNTAX      INTEGER {
                yes (1),
                no (2)
              }
  MAX-ACCESS  read-create
  STATUS      current
  DESCRIPTION "Send SNMP trap when 'qos user-port shutdown' param or
                rule having action=port-disable is matched/invoked?"
  DEFVAL      { yes }
  ::= { alaQoSAppliedRuleEntry 20 }

alaQoSAppliedRuleDefaultList OBJECT-TYPE
  SYNTAX      INTEGER {
                yes (1),
                no (2)
              }
  MAX-ACCESS  read-create
  STATUS      current
  DESCRIPTION "This rule belongs to the default policy list. "
  DEFVAL      { yes }
  ::= { alaQoSAppliedRuleEntry 21 }

alaQoSAppliedRuleGreenPacketCount  OBJECT-TYPE
  SYNTAX      Counter64
  MAX-ACCESS  read-only
  STATUS      current
  DESCRIPTION "Counter for the number of  packets being green compliant."
  ::= { alaQoSAppliedRuleEntry 22 }

alaQoSAppliedRuleYellowPacketCount  OBJECT-TYPE
  SYNTAX      Counter64
  MAX-ACCESS  read-only
  STATUS      current
  DESCRIPTION "Counter for the number of packets being yellow compliant."
  ::= { alaQoSAppliedRuleEntry 23 }

alaQoSAppliedRuleRedPacketCount  OBJECT-TYPE
  SYNTAX      Counter64
  MAX-ACCESS  read-only
  STATUS      current
  DESCRIPTION "Counter for the number of packets being red compliant."
  ::= { alaQoSAppliedRuleEntry 24 }

alaQoSAppliedRuleGreenByteCount  OBJECT-TYPE
  SYNTAX      Counter64
  MAX-ACCESS  read-only
  STATUS      current
  DESCRIPTION "Counter for the number of  packets being green compliant."
  ::= { alaQoSAppliedRuleEntry 25 }

alaQoSAppliedRuleYellowByteCount  OBJECT-TYPE
  SYNTAX      Counter64
  MAX-ACCESS  read-only
  STATUS      current
  DESCRIPTION "Counter for the number of packets being yellow compliant."
  ::= { alaQoSAppliedRuleEntry 26 }

alaQoSAppliedRuleRedByteCount  OBJECT-TYPE
  SYNTAX      Counter64
  MAX-ACCESS  read-only
  STATUS      current
  DESCRIPTION "Counter for the number of packets being red compliant."
  ::= { alaQoSAppliedRuleEntry 27 }


--
-- Definition of condition table
--

alaQoSConditionTable OBJECT-TYPE
  SYNTAX      SEQUENCE OF QoSConditionEntry
  MAX-ACCESS  not-accessible
  STATUS      current
  DESCRIPTION "Table of QoS Condition definitions"
  ::= { alaQoSMIBObjects 3 }

alaQoSConditionEntry OBJECT-TYPE
  SYNTAX      QoSConditionEntry
  MAX-ACCESS  not-accessible
  STATUS      current
  DESCRIPTION "Definition of QoS Condition"
  INDEX {
          alaQoSConditionName
        }
  ::= { alaQoSConditionTable 1 }

QoSConditionEntry ::=
  SEQUENCE
  {
    alaQoSConditionName                                     SnmpAdminString,
    alaQoSConditionSource                                   INTEGER,
    alaQoSConditionSourceSlot                               Integer32,
    alaQoSConditionSourceSlotStatus                         INTEGER,
    alaQoSConditionSourcePort                               Integer32,
    alaQoSConditionSourcePortGroup                          SnmpAdminString,
    alaQoSConditionSourcePortGroupStatus                    INTEGER,
    alaQoSConditionDestinationSlot                          Integer32,
    alaQoSConditionDestinationSlotStatus                    INTEGER,
    alaQoSConditionDestinationPort                          Integer32,
    alaQoSConditionDestinationPortGroup                     SnmpAdminString,
    alaQoSConditionDestinationPortGroupStatus               INTEGER,
    alaQoSConditionSourceMacAddr                            MacAddress,
    alaQoSConditionSourceMacAddrStatus                      INTEGER,
    alaQoSConditionSourceMacMask                            MacAddress,
    alaQoSConditionSourceMacGroup                           SnmpAdminString,
    alaQoSConditionSourceMacGroupStatus                     INTEGER,
    alaQoSConditionDestinationMacAddr                       MacAddress,
    alaQoSConditionDestinationMacAddrStatus                 INTEGER,
    alaQoSConditionDestinationMacMask                       MacAddress,
    alaQoSConditionDestinationMacGroup                      SnmpAdminString,
    alaQoSConditionDestinationMacGroupStatus                INTEGER,
    alaQoSConditionSourceVlan                               Integer32,
    alaQoSConditionSourceVlanStatus                         INTEGER,
    alaQoSConditionDestinationVlan                          Integer32,
    alaQoSConditionDestinationVlanStatus                    INTEGER,
    alaQoSCondition8021p                                    Integer32,
    alaQoSCondition8021pStatus                              INTEGER,
    alaQoSConditionSourceIpAddr                             IpAddress,
    alaQoSConditionSourceIpAddrStatus                       INTEGER,
    alaQoSConditionSourceIpMask                             IpAddress,
    alaQoSConditionSourceNetworkGroup                       SnmpAdminString,
    alaQoSConditionSourceNetworkGroupStatus                 INTEGER,
    alaQoSConditionDestinationIpAddr                        IpAddress,
    alaQoSConditionDestinationIpAddrStatus                  INTEGER,
    alaQoSConditionDestinationIpMask                        IpAddress,
    alaQoSConditionDestinationNetworkGroup                  SnmpAdminString,
    alaQoSConditionDestinationNetworkGroupStatus            INTEGER,
    alaQoSConditionMulticastIpAddr                          IpAddress,
    alaQoSConditionMulticastIpAddrStatus                    INTEGER,
    alaQoSConditionMulticastIpMask                          IpAddress,
    alaQoSConditionMulticastNetworkGroup                    SnmpAdminString,
    alaQoSConditionMulticastNetworkGroupStatus              INTEGER,
    alaQoSConditionTos                                      Integer32,
    alaQoSConditionTosStatus                                INTEGER,
    alaQoSConditionTosMask                                  Integer32,
    alaQoSConditionDscp                                     Integer32,
    alaQoSConditionDscpStatus                               INTEGER,
    alaQoSConditionDscpMask                                 Integer32,
    alaQoSConditionIpProtocol                               Integer32,
    alaQoSConditionIpProtocolStatus                         INTEGER,
    alaQoSConditionSourceIpPort                             Integer32,
    alaQoSConditionSourceIpPortStatus                       INTEGER,
    alaQoSConditionDestinationIpPort                        Integer32,
    alaQoSConditionDestinationIpPortStatus                  INTEGER,
    alaQoSConditionService                                  SnmpAdminString,
    alaQoSConditionServiceStatus                            INTEGER,
    alaQoSConditionServiceGroup                             SnmpAdminString,
    alaQoSConditionServiceGroupStatus                       INTEGER,
    alaQoSConditionIcmpType                                 Integer32,
    alaQoSConditionIcmpTypeStatus                           INTEGER,
    alaQoSConditionIcmpCode                                 Integer32,
    alaQoSConditionIcmpCodeStatus                           INTEGER,
    alaQoSConditionRowStatus                                RowStatus,
    alaQoSConditionSourcePortEnd                            Integer32,
    alaQoSConditionDestinationPortEnd                       Integer32,
    alaQoSConditionSourceIpPortEnd                          Integer32,
    alaQoSConditionDestinationIpPortEnd                     Integer32,
    alaQoSConditionSourceTcpPort                            Integer32,
    alaQoSConditionSourceTcpPortStatus                      INTEGER,
    alaQoSConditionSourceTcpPortEnd                         Integer32,
    alaQoSConditionDestinationTcpPort                       Integer32,
    alaQoSConditionDestinationTcpPortStatus                 INTEGER,
    alaQoSConditionDestinationTcpPortEnd                    Integer32,
    alaQoSConditionSourceUdpPort                            Integer32,
    alaQoSConditionSourceUdpPortStatus                      INTEGER,
    alaQoSConditionSourceUdpPortEnd                         Integer32,
    alaQoSConditionDestinationUdpPort                       Integer32,
    alaQoSConditionDestinationUdpPortStatus                 INTEGER,
    alaQoSConditionDestinationUdpPortEnd                    Integer32,
    alaQoSConditionEthertype                                Integer32,
    alaQoSConditionEthertypeStatus                          INTEGER,
    alaQoSConditionTcpFlags                                 INTEGER,
    alaQoSConditionTcpFlagsStatus                           INTEGER,
    alaQoSConditionTcpFlagsVal                              Integer32,
    alaQoSConditionTcpFlagsValStatus                        INTEGER,
    alaQoSConditionTcpFlagsMask                             Integer32,
    alaQoSConditionTcpFlagsMaskStatus                       INTEGER,
    alaQoSConditionTcpEstablished                           INTEGER,
    alaQoSConditionSourceIpv6Addr                           Ipv6Address,
    alaQoSConditionSourceIpv6AddrStatus                     INTEGER,
    alaQoSConditionSourceIpv6Mask                           Ipv6Address,
    alaQoSConditionDestinationIpv6Addr                      Ipv6Address,
    alaQoSConditionDestinationIpv6AddrStatus                INTEGER,
    alaQoSConditionDestinationIpv6Mask                      Ipv6Address,
    alaQoSConditionIpv6Traffic                              INTEGER,
    alaQoSConditionIpv6NH                                   Integer32,
    alaQoSConditionIpv6NHStatus                             INTEGER,
    alaQoSConditionIpv6FlowLabel                            Integer32,
    alaQoSConditionIpv6FlowLabelStatus                      INTEGER,
    alaQoSConditionMcastIpv6Addr                            Ipv6Address,
    alaQoSConditionMcastIpv6AddrStatus                      INTEGER,
    alaQoSConditionMcastIpv6Mask                            Ipv6Address,
    alaQoSConditionDscpEnd                                  Integer32,
    alaQoSConditionInnerSourceVlan                          Integer32,
    alaQoSConditionInnerSourceVlanStatus                    INTEGER,
    alaQoSConditionInner8021p                               Integer32,
    alaQoSConditionInner8021pStatus                         INTEGER,
    alaQoSConditionVrfName                                  SnmpAdminString,
    alaQoSConditionVrfNameStatus                            INTEGER,
    alaQoSConditionFragments                                INTEGER
  }

alaQoSConditionName OBJECT-TYPE
  SYNTAX      SnmpAdminString (SIZE(0..31))
  MAX-ACCESS  not-accessible
  STATUS      current
  DESCRIPTION "Name of condition"
  ::= { alaQoSConditionEntry 1 }

alaQoSConditionSource OBJECT-TYPE
  SYNTAX      INTEGER {
                ldap (1),
                cli (2),
                blt (3),
                api (4),
                imp (5)
              }
  MAX-ACCESS  read-create
  STATUS      current
  DESCRIPTION "What entity created the condition."
  DEFVAL      { cli }
  ::= { alaQoSConditionEntry 2 }

alaQoSConditionSourceSlot OBJECT-TYPE
  SYNTAX      Integer32 (0..16)
  MAX-ACCESS  read-create
  STATUS      current
  DESCRIPTION "Source physical slot used for traffic classification
               When 0, the port identifies an aggregate"
  DEFVAL      { 1 }
  ::= { alaQoSConditionEntry 3 }

alaQoSConditionSourceSlotStatus OBJECT-TYPE
  SYNTAX      INTEGER {
                enabled (1),
                disabled (2)
              }
  MAX-ACCESS  read-create
  STATUS      current
  DESCRIPTION "Status field indicating whether the source physical slot and
               port range needs to be matched(enabled) or not(disabled)."
  DEFVAL      { disabled }
  ::= { alaQoSConditionEntry 4 }

alaQoSConditionSourcePort OBJECT-TYPE
  SYNTAX      Integer32 (1..52)
  MAX-ACCESS  read-create
  STATUS      current
  DESCRIPTION "Source physical port range start to use for
               traffic classification"
  DEFVAL      { 1 }
  ::= { alaQoSConditionEntry 5 }

alaQoSConditionSourcePortGroup OBJECT-TYPE
  SYNTAX      SnmpAdminString (SIZE(0..31))
  MAX-ACCESS  read-create
  STATUS      current
  DESCRIPTION "Source physical port group to use for traffic classification"
  ::= { alaQoSConditionEntry 6 }

alaQoSConditionSourcePortGroupStatus OBJECT-TYPE
  SYNTAX      INTEGER {
                enabled (1),
                disabled (2)
              }
  MAX-ACCESS  read-create
  STATUS      current
  DESCRIPTION "Status field indicating whether the source physical port group
               needs to be matched(enabled) or not(disabled)."
  DEFVAL      { disabled }
  ::= { alaQoSConditionEntry 7 }

alaQoSConditionDestinationSlot OBJECT-TYPE
  SYNTAX      Integer32 (0..16)
  MAX-ACCESS  read-create
  STATUS      current
  DESCRIPTION "Destination physical slot used for traffic classification
               When 0, the port identifies an aggregate"
  DEFVAL      { 1 }
  ::= { alaQoSConditionEntry 8 }

alaQoSConditionDestinationSlotStatus OBJECT-TYPE
  SYNTAX      INTEGER {
                enabled (1),
                disabled (2)
              }
  MAX-ACCESS  read-create
  STATUS      current
  DESCRIPTION "Status field indicating whether the destination physical slot
               and port range needs to be matched(enabled) or not(disabled)."
  DEFVAL      { disabled }
  ::= { alaQoSConditionEntry 9 }

alaQoSConditionDestinationPort OBJECT-TYPE
  SYNTAX      Integer32 (1..52)
  MAX-ACCESS  read-create
  STATUS      current
  DESCRIPTION "Destination physical port range start to use for traffic
               classification"
  DEFVAL      { 1 }
  ::= { alaQoSConditionEntry 10 }

alaQoSConditionDestinationPortGroup OBJECT-TYPE
  SYNTAX      SnmpAdminString (SIZE(0..31))
  MAX-ACCESS  read-create
  STATUS      current
  DESCRIPTION "Destination physical port group to use for traffic
               classification"
  ::= { alaQoSConditionEntry 11 }

alaQoSConditionDestinationPortGroupStatus OBJECT-TYPE
  SYNTAX      INTEGER {
                enabled (1),
                disabled (2)
              }
  MAX-ACCESS  read-create
  STATUS      current
  DESCRIPTION "Status field indicating whether the destination physical port
               group needs to be matched(enabled) or not(disabled)."
  DEFVAL      { disabled }
  ::= { alaQoSConditionEntry 12 }


alaQoSConditionSourceMacAddr OBJECT-TYPE
  SYNTAX      MacAddress
  MAX-ACCESS  read-create
  STATUS      current
  DESCRIPTION "Source MAC address to use for traffic classification"
  DEFVAL      { '000000000000'h }
  ::= { alaQoSConditionEntry 13 }

alaQoSConditionSourceMacAddrStatus OBJECT-TYPE
  SYNTAX      INTEGER {
                enabled (1),
                disabled (2)
              }
  MAX-ACCESS  read-create
  STATUS      current
  DESCRIPTION "Status field indicating whether the source MAC address & mask
               needs to be matched(enabled) or not(disabled)."
  DEFVAL      { disabled }
  ::= { alaQoSConditionEntry 14 }

alaQoSConditionSourceMacMask OBJECT-TYPE
  SYNTAX      MacAddress
  MAX-ACCESS  read-create
  STATUS      current
  DESCRIPTION "Source MAC mask to use for traffic classification"
  DEFVAL      { 'ffffffffffff'h }
  ::= { alaQoSConditionEntry 15 }

alaQoSConditionSourceMacGroup OBJECT-TYPE
  SYNTAX      SnmpAdminString (SIZE(0..31))
  MAX-ACCESS  read-create
  STATUS      current
  DESCRIPTION "Source MAC group to use for traffic classification"
  ::= { alaQoSConditionEntry 16 }

alaQoSConditionSourceMacGroupStatus OBJECT-TYPE
  SYNTAX      INTEGER {
                enabled (1),
                disabled (2)
              }
  MAX-ACCESS  read-create
  STATUS      current
  DESCRIPTION "Status field indicating whether the source MAC group
               needs to be matched(enabled) or not(disabled)."
  DEFVAL      { disabled }
  ::= { alaQoSConditionEntry 17 }

alaQoSConditionDestinationMacAddr OBJECT-TYPE
  SYNTAX      MacAddress
  MAX-ACCESS  read-create
  STATUS      current
  DESCRIPTION "Destination MAC address to use for traffic classification"
  DEFVAL      { '000000000000'h }
  ::= { alaQoSConditionEntry 18 }

alaQoSConditionDestinationMacAddrStatus OBJECT-TYPE
  SYNTAX      INTEGER {
                enabled (1),
                disabled (2)
              }
  MAX-ACCESS  read-create
  STATUS      current
  DESCRIPTION "Status field indicating whether the destination MAC address
               & mask needs to be matched(enabled) or not(disabled)."
  DEFVAL      { disabled }
  ::= { alaQoSConditionEntry 19 }

alaQoSConditionDestinationMacMask OBJECT-TYPE
  SYNTAX      MacAddress
  MAX-ACCESS  read-create
  STATUS      current
  DESCRIPTION "Destination MAC mask to use for traffic classification"
  DEFVAL      { 'ffffffffffff'h }
  ::= { alaQoSConditionEntry 20 }

alaQoSConditionDestinationMacGroup OBJECT-TYPE
  SYNTAX      SnmpAdminString (SIZE(0..31))
  MAX-ACCESS  read-create
  STATUS      current
  DESCRIPTION "Destination MAC group to use for traffic classification"
  ::= { alaQoSConditionEntry 21 }

alaQoSConditionDestinationMacGroupStatus OBJECT-TYPE
  SYNTAX      INTEGER {
                enabled (1),
                disabled (2)
              }
  MAX-ACCESS  read-create
  STATUS      current
  DESCRIPTION "Status field indicating whether the destination MAC group
               needs to be matched(enabled) or not(disabled)."
  DEFVAL      { disabled }
  ::= { alaQoSConditionEntry 22 }

alaQoSConditionSourceVlan OBJECT-TYPE
  SYNTAX      Integer32 (0..4095)
  MAX-ACCESS  read-create
  STATUS      current
  DESCRIPTION "Source VLAN to use for traffic classification"
  DEFVAL      { 0 }
  ::= { alaQoSConditionEntry 23 }

alaQoSConditionSourceVlanStatus OBJECT-TYPE
  SYNTAX      INTEGER {
                enabled (1),
                disabled (2)
              }
  MAX-ACCESS  read-create
  STATUS      current
  DESCRIPTION "Status field indicating whether the source VLAN
               needs to be matched(enabled) or not(disabled)."
  DEFVAL      { disabled }
  ::= { alaQoSConditionEntry 24 }

alaQoSConditionDestinationVlan OBJECT-TYPE
  SYNTAX      Integer32 (0..4095)
  MAX-ACCESS  read-create
  STATUS      current
  DESCRIPTION "Destination VLAN to use for traffic classification"
  DEFVAL      { 0 }
  ::= { alaQoSConditionEntry 25 }

alaQoSConditionDestinationVlanStatus OBJECT-TYPE
  SYNTAX      INTEGER {
                enabled (1),
                disabled (2)
              }
  MAX-ACCESS  read-create
  STATUS      current
  DESCRIPTION "Status field indicating whether the destination VLAN
               needs to be matched(enabled) or not(disabled)."
  DEFVAL      { disabled }
  ::= { alaQoSConditionEntry 26 }

alaQoSCondition8021p OBJECT-TYPE
  SYNTAX      Integer32 (0..7)
  MAX-ACCESS  read-create
  STATUS      current
  DESCRIPTION "802.1p value to use for traffic classification"
  DEFVAL      { 0 }
  ::= { alaQoSConditionEntry 27 }

alaQoSCondition8021pStatus OBJECT-TYPE
  SYNTAX      INTEGER {
                enabled (1),
                disabled (2)
              }
  MAX-ACCESS  read-create
  STATUS      current
  DESCRIPTION "Status field indicating whether the 802.1p value
               needs to be matched(enabled) or not(disabled)."
  DEFVAL      { disabled }
  ::= { alaQoSConditionEntry 28 }

alaQoSConditionSourceIpAddr OBJECT-TYPE
  SYNTAX      IpAddress
  MAX-ACCESS  read-create
  STATUS      current
  DESCRIPTION "Source IP address to use for traffic classification"
  DEFVAL      { '00000000'h }
  ::= { alaQoSConditionEntry 29 }

alaQoSConditionSourceIpAddrStatus OBJECT-TYPE
  SYNTAX      INTEGER {
                enabled (1),
                disabled (2)
              }
  MAX-ACCESS  read-create
  STATUS      current
  DESCRIPTION "Status field indicating whether the source IP address & mask
               needs to be matched(enabled) or not(disabled)."
  DEFVAL      { disabled }
  ::= { alaQoSConditionEntry 30 }

alaQoSConditionSourceIpMask OBJECT-TYPE
  SYNTAX      IpAddress
  MAX-ACCESS  read-create
  STATUS      current
  DESCRIPTION "Source IP mask to use for traffic classification"
  DEFVAL      { 'ffffffff'h }
  ::= { alaQoSConditionEntry 31 }

alaQoSConditionSourceNetworkGroup OBJECT-TYPE
  SYNTAX      SnmpAdminString (SIZE(0..31))
  MAX-ACCESS  read-create
  STATUS      current
  DESCRIPTION "Source network group to use for traffic classification"
  ::= { alaQoSConditionEntry 32 }

alaQoSConditionSourceNetworkGroupStatus OBJECT-TYPE
  SYNTAX      INTEGER {
                enabled (1),
                disabled (2)
              }
  MAX-ACCESS  read-create
  STATUS      current
  DESCRIPTION "Status field indicating whether the source network group
               needs to be matched(enabled) or not(disabled)."
  DEFVAL      { disabled }
  ::= { alaQoSConditionEntry 33 }

alaQoSConditionDestinationIpAddr OBJECT-TYPE
  SYNTAX      IpAddress
  MAX-ACCESS  read-create
  STATUS      current
  DESCRIPTION "Destination IP address to use for traffic classification"
  DEFVAL      { '00000000'h }
  ::= { alaQoSConditionEntry 34 }

alaQoSConditionDestinationIpAddrStatus OBJECT-TYPE
  SYNTAX      INTEGER {
                enabled (1),
                disabled (2)
              }
  MAX-ACCESS  read-create
  STATUS      current
  DESCRIPTION "Status field indicating whether the destination IP address
               & mask needs to be matched(enabled) or not(disabled)."
  DEFVAL      { disabled }
  ::= { alaQoSConditionEntry 35 }

alaQoSConditionDestinationIpMask OBJECT-TYPE
  SYNTAX      IpAddress
  MAX-ACCESS  read-create
  STATUS      current
  DESCRIPTION "Destination IP mask to use for traffic classification"
  DEFVAL      { 'ffffffff'h }
  ::= { alaQoSConditionEntry 36 }

alaQoSConditionDestinationNetworkGroup OBJECT-TYPE
  SYNTAX      SnmpAdminString (SIZE(0..31))
  MAX-ACCESS  read-create
  STATUS      current
  DESCRIPTION "Destination network group to use for traffic classification"
  ::= { alaQoSConditionEntry 37 }

alaQoSConditionDestinationNetworkGroupStatus OBJECT-TYPE
  SYNTAX      INTEGER {
                enabled (1),
                disabled (2)
              }
  MAX-ACCESS  read-create
  STATUS      current
  DESCRIPTION "Status field indicating whether the destination network group
               needs to be matched(enabled) or not(disabled)."
  DEFVAL      { disabled }
  ::= { alaQoSConditionEntry 38 }

alaQoSConditionMulticastIpAddr OBJECT-TYPE
  SYNTAX      IpAddress
  MAX-ACCESS  read-create
  STATUS      current
  DESCRIPTION "Multicast IP address to use for traffic classification"
  DEFVAL      { '00000000'h }
  ::= { alaQoSConditionEntry 39 }

alaQoSConditionMulticastIpAddrStatus OBJECT-TYPE
  SYNTAX      INTEGER {
                enabled (1),
                disabled (2)
              }
  MAX-ACCESS  read-create
  STATUS      current
  DESCRIPTION "Status field indicating whether the multicast IP address & mask
               needs to be matched(enabled) or not(disabled)."
  DEFVAL      { disabled }
  ::= { alaQoSConditionEntry 40 }

alaQoSConditionMulticastIpMask OBJECT-TYPE
  SYNTAX      IpAddress
  MAX-ACCESS  read-create
  STATUS      current
  DESCRIPTION "Multicast IP mask to use for traffic classification"
  DEFVAL      { 'ffffffff'h }
  ::= { alaQoSConditionEntry 41 }

alaQoSConditionMulticastNetworkGroup OBJECT-TYPE
  SYNTAX      SnmpAdminString (SIZE(0..31))
  MAX-ACCESS  read-create
  STATUS      current
  DESCRIPTION "Multicast network group to use for traffic classification"
  ::= { alaQoSConditionEntry 42 }

alaQoSConditionMulticastNetworkGroupStatus OBJECT-TYPE
  SYNTAX      INTEGER {
                enabled (1),
                disabled (2)
              }
  MAX-ACCESS  read-create
  STATUS      current
  DESCRIPTION "Status field indicating whether the multicast network group
               needs to be matched(enabled) or not(disabled)."
  DEFVAL      { disabled }
  ::= { alaQoSConditionEntry 43 }

alaQoSConditionTos OBJECT-TYPE
  SYNTAX      Integer32 (0..7)
  MAX-ACCESS  read-create
  STATUS      current
  DESCRIPTION "TOS value to use for traffic classification"
  DEFVAL      { 0 }
  ::= { alaQoSConditionEntry 44 }

alaQoSConditionTosStatus OBJECT-TYPE
  SYNTAX      INTEGER {
                enabled (1),
                disabled (2)
              }
  MAX-ACCESS  read-create
  STATUS      current
  DESCRIPTION "Status field indicating whether the TOS value & mask
               needs to be matched(enabled) or not(disabled)."
  DEFVAL      { disabled }
  ::= { alaQoSConditionEntry 45 }

alaQoSConditionTosMask OBJECT-TYPE
  SYNTAX      Integer32 (0..7)
  MAX-ACCESS  read-create
  STATUS      current
  DESCRIPTION "TOS mask to use for traffic classification"
  DEFVAL      { 7 }
  ::= { alaQoSConditionEntry 46 }

alaQoSConditionDscp OBJECT-TYPE
  SYNTAX      Integer32 (0..63)
  MAX-ACCESS  read-create
  STATUS      current
  DESCRIPTION "DSCP value to use for traffic classification"
  DEFVAL      { 0 }
  ::= { alaQoSConditionEntry 47 }

alaQoSConditionDscpStatus OBJECT-TYPE
  SYNTAX      INTEGER {
                enabled (1),
                disabled (2)
              }
  MAX-ACCESS  read-create
  STATUS      current
  DESCRIPTION "Status field indicating whether the DSCP value & mask
               needs to be matched(enabled) or not(disabled)."
  DEFVAL      { disabled }
  ::= { alaQoSConditionEntry 48 }

alaQoSConditionDscpMask OBJECT-TYPE
  SYNTAX      Integer32 (0..63)
  MAX-ACCESS  read-create
  STATUS      current
  DESCRIPTION "DSCP mask to use for traffic classification"
  DEFVAL      { 63 }
  ::= { alaQoSConditionEntry 49 }

alaQoSConditionIpProtocol OBJECT-TYPE
  SYNTAX      Integer32 (0..255)
  MAX-ACCESS  read-create
  STATUS      current
  DESCRIPTION "IP protocol to use for traffic classification."
  DEFVAL      { 0 }
  ::= { alaQoSConditionEntry 50 }

alaQoSConditionIpProtocolStatus OBJECT-TYPE
  SYNTAX      INTEGER {
                enabled (1),
                disabled (2)
              }
  MAX-ACCESS  read-create
  STATUS      current
  DESCRIPTION "Status field indicating whether the IP protocol
               needs to be matched(enabled) or not(disabled)."
  DEFVAL      { disabled }
  ::= { alaQoSConditionEntry 51 }

alaQoSConditionSourceIpPort OBJECT-TYPE
  SYNTAX      Integer32 (0..65535)
  MAX-ACCESS  read-create
  STATUS      current
  DESCRIPTION "Source IP port range start to use for traffic classification."
  ::= { alaQoSConditionEntry 52 }

alaQoSConditionSourceIpPortStatus OBJECT-TYPE
  SYNTAX      INTEGER {
                enabled (1),
                disabled (2)
              }
  MAX-ACCESS  read-create
  STATUS      current
  DESCRIPTION "Status field indicating whether the source IP port range
               needs to be matched(enabled) or not(disabled)."
  DEFVAL      { disabled }
  ::= { alaQoSConditionEntry 53 }

alaQoSConditionDestinationIpPort OBJECT-TYPE
  SYNTAX      Integer32 (0..65535)
  MAX-ACCESS  read-create
  STATUS      current
  DESCRIPTION "Destination IP port range start to use for traffic
               classification."
  ::= { alaQoSConditionEntry 54 }

alaQoSConditionDestinationIpPortStatus OBJECT-TYPE
  SYNTAX      INTEGER {
                enabled (1),
                disabled (2)
              }
  MAX-ACCESS  read-create
  STATUS      current
  DESCRIPTION "Status field indicating whether the destination IP port range
               needs to be matched(enabled) or not(disabled)."
  DEFVAL      { disabled }
  ::= { alaQoSConditionEntry 55 }

alaQoSConditionService OBJECT-TYPE
  SYNTAX      SnmpAdminString (SIZE(0..31))
  MAX-ACCESS  read-create
  STATUS      current
  DESCRIPTION "Name of service to use for traffic classification"
  ::= { alaQoSConditionEntry 56 }

alaQoSConditionServiceStatus OBJECT-TYPE
  SYNTAX      INTEGER {
                enabled (1),
                disabled (2)
              }
  MAX-ACCESS  read-create
  STATUS      current
  DESCRIPTION "Status field indicating whether the service
               needs to be matched(enabled) or not(disabled)."
  DEFVAL      { disabled }
  ::= { alaQoSConditionEntry 57 }

alaQoSConditionServiceGroup OBJECT-TYPE
  SYNTAX      SnmpAdminString (SIZE(0..31))
  MAX-ACCESS  read-create
  STATUS      current
  DESCRIPTION "Name of service group to use for traffic classification"
  ::= { alaQoSConditionEntry 58 }

alaQoSConditionServiceGroupStatus OBJECT-TYPE
  SYNTAX      INTEGER {
                enabled (1),
                disabled (2)
              }
  MAX-ACCESS  read-create
  STATUS      current
  DESCRIPTION "Status field indicating whether the service group
               needs to be matched(enabled) or not(disabled)."
  DEFVAL      { disabled }
  ::= { alaQoSConditionEntry 59 }

alaQoSConditionIcmpType OBJECT-TYPE
  SYNTAX      Integer32 (0..255)
  MAX-ACCESS  read-create
  STATUS      current
  DESCRIPTION "ICMP type to use for traffic classification"
  DEFVAL      { 0 }
  ::= { alaQoSConditionEntry 60 }

alaQoSConditionIcmpTypeStatus OBJECT-TYPE
  SYNTAX      INTEGER {
                enabled (1),
                disabled (2)
              }
  MAX-ACCESS  read-create
  STATUS      current
  DESCRIPTION "Status field indicating whether the ICMP type
               needs to be matched(enabled) or not(disabled)."
  DEFVAL      { disabled }
  ::= { alaQoSConditionEntry 61 }

alaQoSConditionIcmpCode OBJECT-TYPE
  SYNTAX      Integer32 (0..255)
  MAX-ACCESS  read-create
  STATUS      current
  DESCRIPTION "ICMP code to use for traffic classification"
  DEFVAL      { 0 }
  ::= { alaQoSConditionEntry 62 }

alaQoSConditionIcmpCodeStatus OBJECT-TYPE
  SYNTAX      INTEGER {
                enabled (1),
                disabled (2)
              }
  MAX-ACCESS  read-create
  STATUS      current
  DESCRIPTION "Status field indicating whether the ICMP code
               needs to be matched(enabled) or not(disabled)."
  DEFVAL      { disabled }
  ::= { alaQoSConditionEntry 63 }

alaQoSConditionRowStatus OBJECT-TYPE
  SYNTAX      RowStatus
  MAX-ACCESS  read-create
  STATUS      current
  DESCRIPTION "Used to create/delete conditions according to the
               RowStatus convention"
  ::= { alaQoSConditionEntry 64 }

alaQoSConditionSourcePortEnd OBJECT-TYPE
  SYNTAX      Integer32 (1..52)
  MAX-ACCESS  read-create
  STATUS      current
  DESCRIPTION "Source physical port range end to use for traffic
               classification.  Must be greater than port range start to
               indicate a range.  When '1', use source port as a single port."
  DEFVAL      { 1 }
  ::= { alaQoSConditionEntry 65 }

alaQoSConditionDestinationPortEnd OBJECT-TYPE
  SYNTAX      Integer32 (1..52)
  MAX-ACCESS  read-create
  STATUS      current
  DESCRIPTION "Destination physical port range end to use for traffic
               classification.  Must be greater than port range start to
               indicate a range.  When '1', use destination port as a single
               port."
  DEFVAL      { 1 }
  ::= { alaQoSConditionEntry 66 }

alaQoSConditionSourceIpPortEnd OBJECT-TYPE
  SYNTAX      Integer32 (0..65535)
  MAX-ACCESS  read-create
  STATUS      current
  DESCRIPTION "Source IP port range end to use for traffic classification.
               Must be greater than source IP port range start to indicate a
               range.  When '0', use source IP port as a single IP port."
  ::= { alaQoSConditionEntry 67 }

alaQoSConditionDestinationIpPortEnd OBJECT-TYPE
  SYNTAX      Integer32 (0..65535)
  MAX-ACCESS  read-create
  STATUS      current
  DESCRIPTION "Destination IP port range end to use for traffic classification.
               Must be greater than destination IP port range start to indicate
               a range.  When '0', use destination IP port as a single IP port."
  ::= { alaQoSConditionEntry 68 }

alaQoSConditionSourceTcpPort OBJECT-TYPE
  SYNTAX      Integer32 (0..65535)
  MAX-ACCESS  read-create
  STATUS      current
  DESCRIPTION "Source TCP port range start to use for traffic classification."
  ::= { alaQoSConditionEntry 69 }

alaQoSConditionSourceTcpPortStatus OBJECT-TYPE
  SYNTAX      INTEGER {
                enabled (1),
                disabled (2)
              }
  MAX-ACCESS  read-create
  STATUS      current
  DESCRIPTION "Status field indicating whether the source TCP port range
               needs to be matched(enabled) or not(disabled)."
  DEFVAL      { disabled }
  ::= { alaQoSConditionEntry 70 }

alaQoSConditionSourceTcpPortEnd OBJECT-TYPE
  SYNTAX      Integer32 (0..65535)
  MAX-ACCESS  read-create
  STATUS      current
  DESCRIPTION "Source TCP port range end to use for traffic classification.
               Must be greater than source TCP port range start to indicate a
               range.  When '0', use source TCP port as a single TCP port."
  ::= { alaQoSConditionEntry 71 }

alaQoSConditionDestinationTcpPort OBJECT-TYPE
  SYNTAX      Integer32 (0..65535)
  MAX-ACCESS  read-create
  STATUS      current
  DESCRIPTION "Destination TCP port range start to use for traffic
               classification."
  ::= { alaQoSConditionEntry 72 }

alaQoSConditionDestinationTcpPortStatus OBJECT-TYPE
  SYNTAX      INTEGER {
                enabled (1),
                disabled (2)
              }
  MAX-ACCESS  read-create
  STATUS      current
  DESCRIPTION "Status field indicating whether the destination TCP port range
               needs to be matched(enabled) or not(disabled)."
  DEFVAL      { disabled }
  ::= { alaQoSConditionEntry 73 }

alaQoSConditionDestinationTcpPortEnd OBJECT-TYPE
  SYNTAX      Integer32 (0..65535)
  MAX-ACCESS  read-create
  STATUS      current
  DESCRIPTION "Destination TCP port range end to use for traffic
               classification.  Must be greater than destination TCP port range
               start to indicate a range.  When '0', use destination TCP port
               as a single TCP port."
  ::= { alaQoSConditionEntry 74 }

alaQoSConditionSourceUdpPort OBJECT-TYPE
  SYNTAX      Integer32 (0..65535)
  MAX-ACCESS  read-create
  STATUS      current
  DESCRIPTION "Source UDP port range start to use for traffic classification."
  ::= { alaQoSConditionEntry 75 }

alaQoSConditionSourceUdpPortStatus OBJECT-TYPE
  SYNTAX      INTEGER {
                enabled (1),
                disabled (2)
              }
  MAX-ACCESS  read-create
  STATUS      current
  DESCRIPTION "Status field indicating whether the source UDP port range
               needs to be matched(enabled) or not(disabled)."
  DEFVAL      { disabled }
  ::= { alaQoSConditionEntry 76 }

alaQoSConditionSourceUdpPortEnd OBJECT-TYPE
  SYNTAX      Integer32 (0..65535)
  MAX-ACCESS  read-create
  STATUS      current
  DESCRIPTION "Source UDP port range end to use for traffic classification.
               Must be greater than source UDP port range start to indicate
               a range.  When '0', use source UDP port as a single UDP port."
  ::= { alaQoSConditionEntry 77 }

alaQoSConditionDestinationUdpPort OBJECT-TYPE
  SYNTAX      Integer32 (0..65535)
  MAX-ACCESS  read-create
  STATUS      current
  DESCRIPTION "Destination UDP port range start to use for traffic
               classification."
  ::= { alaQoSConditionEntry 78 }

alaQoSConditionDestinationUdpPortStatus OBJECT-TYPE
  SYNTAX      INTEGER {
                enabled (1),
                disabled (2)
              }
  MAX-ACCESS  read-create
  STATUS      current
  DESCRIPTION "Status field indicating whether the destination UDP port range
               needs to be matched(enabled) or not(disabled)."
  DEFVAL      { disabled }
  ::= { alaQoSConditionEntry 79 }

alaQoSConditionDestinationUdpPortEnd OBJECT-TYPE
  SYNTAX      Integer32 (0..65535)
  MAX-ACCESS  read-create
  STATUS      current
  DESCRIPTION "Destination UDP port range end to use for traffic
               classification.  Must be greater than destination UDP port range
               start to indicate a range.  When '0', use destination UDP port
               as a single TCP port."
  ::= { alaQoSConditionEntry 80 }

alaQoSConditionEthertype OBJECT-TYPE
  SYNTAX      Integer32 (0..65535)
  MAX-ACCESS  read-create
  STATUS      current
  DESCRIPTION "Ethertype value to use for traffic classification"
  DEFVAL      { 0 }
  ::= { alaQoSConditionEntry 81 }

alaQoSConditionEthertypeStatus OBJECT-TYPE
  SYNTAX      INTEGER {
                enabled (1),
                disabled (2)
              }
  MAX-ACCESS  read-create
  STATUS      current
  DESCRIPTION "Status field indicating whether the ethertype value
               needs to be matched(enabled) or not(disabled)."
  DEFVAL      { disabled }
  ::= { alaQoSConditionEntry 82 }

alaQoSConditionTcpFlags OBJECT-TYPE
  SYNTAX      INTEGER {
                all (1),
                any (2)
              }
  MAX-ACCESS  read-create
  STATUS      current
  DESCRIPTION "Use any/all specifieid TCP flags for traffic classification"
  DEFVAL      { all }
  ::= { alaQoSConditionEntry 83 }

alaQoSConditionTcpFlagsStatus OBJECT-TYPE
  SYNTAX      INTEGER {
                enabled (1),
                disabled (2)
              }
  MAX-ACCESS  read-create
  STATUS      current
  DESCRIPTION "Status field indicating whether the TCP flag bits
               needs to be matched(enabled) or not(disabled)."
  DEFVAL      { disabled }
  ::= { alaQoSConditionEntry 84 }

alaQoSConditionTcpFlagsVal OBJECT-TYPE
  SYNTAX      Integer32
  MAX-ACCESS  read-create
  STATUS      current
  DESCRIPTION "TCP flags values used for traffic classification"
  ::= { alaQoSConditionEntry 85 }

alaQoSConditionTcpFlagsValStatus OBJECT-TYPE
  SYNTAX      INTEGER {
                enabled (1),
                disabled (2)
              }
  MAX-ACCESS  read-create
  STATUS      current
  DESCRIPTION "Not used"
  DEFVAL      { disabled }
  ::= { alaQoSConditionEntry 86 }

alaQoSConditionTcpFlagsMask OBJECT-TYPE
  SYNTAX      Integer32
  MAX-ACCESS  read-create
  STATUS      current
  DESCRIPTION "Mask of TCP flags bits used for traffic classification"
  ::= { alaQoSConditionEntry 87 }

alaQoSConditionTcpFlagsMaskStatus OBJECT-TYPE
  SYNTAX      INTEGER {
                enabled (1),
                disabled (2)
              }
  MAX-ACCESS  read-create
  STATUS      current
  DESCRIPTION "Not used"
  DEFVAL      { disabled }
  ::= { alaQoSConditionEntry 88 }

alaQoSConditionTcpEstablished OBJECT-TYPE
  SYNTAX      INTEGER {
                yes (1),
                no (2)
              }
  MAX-ACCESS  read-create
  STATUS      current
  DESCRIPTION "Look for established TCP sessions in classification"
  DEFVAL      { no }
  ::= { alaQoSConditionEntry 89 }

alaQoSConditionSourceIpv6Addr OBJECT-TYPE
  SYNTAX      Ipv6Address
  MAX-ACCESS  read-create
  STATUS      current
  DESCRIPTION "Source IPv6 address to use for traffic classification"
  DEFVAL      { '00000000000000000000000000000000'h }
  ::= { alaQoSConditionEntry 90 }

alaQoSConditionSourceIpv6AddrStatus OBJECT-TYPE
  SYNTAX      INTEGER {
                enabled (1),
                disabled (2)
              }
  MAX-ACCESS  read-create
  STATUS      current
  DESCRIPTION "Status field indicating whether the source IPv6 address & mask
               needs to be matched(enabled) or not(disabled)."
  DEFVAL      { disabled }
  ::= { alaQoSConditionEntry 91 }

alaQoSConditionSourceIpv6Mask OBJECT-TYPE
  SYNTAX      Ipv6Address
  MAX-ACCESS  read-create
  STATUS      current
  DESCRIPTION "Source IPv6 mask to use for traffic classification"
  DEFVAL      { 'ffffffffffffffffffffffffffffffff'h }
  ::= { alaQoSConditionEntry 92 }

alaQoSConditionDestinationIpv6Addr OBJECT-TYPE
  SYNTAX      Ipv6Address
  MAX-ACCESS  read-create
  STATUS      current
  DESCRIPTION "Destination IPv6 address to use for traffic classification"
  DEFVAL      { '00000000000000000000000000000000'h }
  ::= { alaQoSConditionEntry 93 }

alaQoSConditionDestinationIpv6AddrStatus OBJECT-TYPE
  SYNTAX      INTEGER {
                enabled (1),
                disabled (2)
              }
  MAX-ACCESS  read-create
  STATUS      current
  DESCRIPTION "Status field indicating whether the destination IPv6 address & mask
               needs to be matched(enabled) or not(disabled)."
  DEFVAL      { disabled }
  ::= { alaQoSConditionEntry 94 }

alaQoSConditionDestinationIpv6Mask OBJECT-TYPE
  SYNTAX      Ipv6Address
  MAX-ACCESS  read-create
  STATUS      current
  DESCRIPTION "Destination IPv6 mask to use for traffic classification"
  DEFVAL      { 'ffffffffffffffffffffffffffffffff'h }
  ::= { alaQoSConditionEntry 95 }

alaQoSConditionIpv6Traffic OBJECT-TYPE
  SYNTAX      INTEGER {
                yes (1),
                no (2)
              }
  MAX-ACCESS  read-create
  STATUS      current
  DESCRIPTION "classify IPV6 traffic "
  ::= { alaQoSConditionEntry 96 }

alaQoSConditionIpv6NH OBJECT-TYPE
  SYNTAX      Integer32 (0..255)
  MAX-ACCESS  read-create
  STATUS      current
  DESCRIPTION "NH value to use for traffic classification"
  DEFVAL      { 0 }
  ::= { alaQoSConditionEntry 97 }

alaQoSConditionIpv6NHStatus OBJECT-TYPE
  SYNTAX      INTEGER {
                enabled (1),
                disabled (2)
              }
  MAX-ACCESS  read-create
  STATUS      current
  DESCRIPTION "Status field indicating whether the NH value
               needs to be matched(enabled) or not(disabled)."
  DEFVAL      { disabled }
  ::= { alaQoSConditionEntry 98 }

alaQoSConditionIpv6FlowLabel OBJECT-TYPE
  SYNTAX      Integer32 (0..1048575)
  MAX-ACCESS  read-create
  STATUS      current
  DESCRIPTION "FL value to use for traffic classification"
  DEFVAL      { 0 }
  ::= { alaQoSConditionEntry 99 }

alaQoSConditionIpv6FlowLabelStatus OBJECT-TYPE
  SYNTAX      INTEGER {
                enabled (1),
                disabled (2)
              }
  MAX-ACCESS  read-create
  STATUS      current
  DESCRIPTION "Status field indicating whether the flow label value
               needs to be matched(enabled) or not(disabled)."
  DEFVAL      { disabled }
  ::= { alaQoSConditionEntry 100 }

alaQoSConditionMcastIpv6Addr OBJECT-TYPE
  SYNTAX      Ipv6Address
  MAX-ACCESS  read-create
  STATUS      current
  DESCRIPTION "Multicast IPv6 address to use for traffic classification"
  DEFVAL      { '00000000000000000000000000000000'h }
  ::= { alaQoSConditionEntry 101 }

alaQoSConditionMcastIpv6AddrStatus OBJECT-TYPE
  SYNTAX      INTEGER {
                enabled (1),
                disabled (2)
              }
  MAX-ACCESS  read-create
  STATUS      current
  DESCRIPTION "Status field indicating whether the multicast IPv6 address & mask
               needs to be matched(enabled) or not(disabled)."
  DEFVAL      { disabled }
  ::= { alaQoSConditionEntry 102 }

alaQoSConditionMcastIpv6Mask OBJECT-TYPE
  SYNTAX      Ipv6Address
  MAX-ACCESS  read-create
  STATUS      current
  DESCRIPTION "Multicast IPv6 mask to use for traffic classification"
  DEFVAL      { 'ffffffffffffffffffffffffffffffff'h }
  ::= { alaQoSConditionEntry 103 }

alaQoSConditionDscpEnd OBJECT-TYPE
  SYNTAX      Integer32 (0..63)
  MAX-ACCESS  read-create
  STATUS      current
  DESCRIPTION "DSCP value to use for traffic classification"
  DEFVAL      { 0 }
  ::= { alaQoSConditionEntry 104 }

alaQoSConditionInnerSourceVlan OBJECT-TYPE
  SYNTAX      Integer32 (0..4095)
  MAX-ACCESS  read-create
  STATUS      current
  DESCRIPTION "Customer VLAN to use for traffic classification"
  DEFVAL      { 0 }
  ::= { alaQoSConditionEntry 105 }

alaQoSConditionInnerSourceVlanStatus OBJECT-TYPE
  SYNTAX      INTEGER {
                enabled (1),
                disabled (2)
              }
  MAX-ACCESS  read-create
  STATUS      current
  DESCRIPTION "Status field indicating whether the inner VLAN
               needs to be matched(enabled) or not(disabled)."
  DEFVAL      { disabled }
  ::= { alaQoSConditionEntry 106 }

alaQoSConditionInner8021p OBJECT-TYPE
  SYNTAX      Integer32 (0..7)
  MAX-ACCESS  read-create
  STATUS      current
  DESCRIPTION "Customer 802.1p to use for traffic classification"
  DEFVAL      { 0 }
  ::= { alaQoSConditionEntry 107 }

alaQoSConditionInner8021pStatus OBJECT-TYPE
  SYNTAX      INTEGER {
                enabled (1),
                disabled (2)
              }
  MAX-ACCESS  read-create
  STATUS      current
  DESCRIPTION "Status field indicating whether the inner 802.1p
               needs to be matched(enabled) or not(disabled)."
  DEFVAL      { disabled }
  ::= { alaQoSConditionEntry 108 }

alaQoSConditionVrfName OBJECT-TYPE
  SYNTAX      SnmpAdminString (SIZE(0..31))
  MAX-ACCESS  read-create
  STATUS      current
  DESCRIPTION "Name of Vrf to match traffic in"
  ::= { alaQoSConditionEntry 109 }

alaQoSConditionVrfNameStatus OBJECT-TYPE
  SYNTAX      INTEGER {
                enabled (1),
                disabled (2)
              }
  MAX-ACCESS  read-create
  STATUS      current
  DESCRIPTION "Status field indicating whether the traffic from a specific vrf needs to be matched(enabled) or not(disabled)."
  DEFVAL      { disabled }
  ::= { alaQoSConditionEntry 110 }

alaQoSConditionFragments OBJECT-TYPE
  SYNTAX      INTEGER {
                yes (1),
                no (2)
              }
  MAX-ACCESS  read-create
  STATUS      current
  DESCRIPTION "TCP packet fragments"
  DEFVAL      { no }
  ::= { alaQoSConditionEntry 111 }


--
-- Definition of condition table
--

alaQoSAppliedConditionTable OBJECT-TYPE
  SYNTAX      SEQUENCE OF QoSAppliedConditionEntry
  MAX-ACCESS  not-accessible
  STATUS      current
  DESCRIPTION "Table of QoS AppliedCondition definitions"
  ::= { alaQoSMIBObjects 4 }

alaQoSAppliedConditionEntry OBJECT-TYPE
  SYNTAX      QoSAppliedConditionEntry
  MAX-ACCESS  not-accessible
  STATUS      current
  DESCRIPTION "Definition of QoS AppliedCondition"
  INDEX {
          alaQoSAppliedConditionName
        }
  ::= { alaQoSAppliedConditionTable 1 }

QoSAppliedConditionEntry ::=
  SEQUENCE
  {
    alaQoSAppliedConditionName                              SnmpAdminString,
    alaQoSAppliedConditionSource                            INTEGER,
    alaQoSAppliedConditionSourceSlot                        Integer32,
    alaQoSAppliedConditionSourceSlotStatus                  INTEGER,
    alaQoSAppliedConditionSourcePort                        Integer32,
    alaQoSAppliedConditionSourcePortGroup                   SnmpAdminString,
    alaQoSAppliedConditionSourcePortGroupStatus             INTEGER,
    alaQoSAppliedConditionDestinationSlot                   Integer32,
    alaQoSAppliedConditionDestinationSlotStatus             INTEGER,
    alaQoSAppliedConditionDestinationPort                   Integer32,
    alaQoSAppliedConditionDestinationPortGroup              SnmpAdminString,
    alaQoSAppliedConditionDestinationPortGroupStatus        INTEGER,
    alaQoSAppliedConditionSourceMacAddr                     MacAddress,
    alaQoSAppliedConditionSourceMacAddrStatus               INTEGER,
    alaQoSAppliedConditionSourceMacMask                     MacAddress,
    alaQoSAppliedConditionSourceMacGroup                    SnmpAdminString,
    alaQoSAppliedConditionSourceMacGroupStatus              INTEGER,
    alaQoSAppliedConditionDestinationMacAddr                MacAddress,
    alaQoSAppliedConditionDestinationMacAddrStatus          INTEGER,
    alaQoSAppliedConditionDestinationMacMask                MacAddress,
    alaQoSAppliedConditionDestinationMacGroup               SnmpAdminString,
    alaQoSAppliedConditionDestinationMacGroupStatus         INTEGER,
    alaQoSAppliedConditionSourceVlan                        Integer32,
    alaQoSAppliedConditionSourceVlanStatus                  INTEGER,
    alaQoSAppliedConditionDestinationVlan                   Integer32,
    alaQoSAppliedConditionDestinationVlanStatus             INTEGER,
    alaQoSAppliedCondition8021p                             Integer32,
    alaQoSAppliedCondition8021pStatus                       INTEGER,
    alaQoSAppliedConditionSourceIpAddr                      IpAddress,
    alaQoSAppliedConditionSourceIpAddrStatus                INTEGER,
    alaQoSAppliedConditionSourceIpMask                      IpAddress,
    alaQoSAppliedConditionSourceNetworkGroup                SnmpAdminString,
    alaQoSAppliedConditionSourceNetworkGroupStatus          INTEGER,
    alaQoSAppliedConditionDestinationIpAddr                 IpAddress,
    alaQoSAppliedConditionDestinationIpAddrStatus           INTEGER,
    alaQoSAppliedConditionDestinationIpMask                 IpAddress,
    alaQoSAppliedConditionDestinationNetworkGroup           SnmpAdminString,
    alaQoSAppliedConditionDestinationNetworkGroupStatus     INTEGER,
    alaQoSAppliedConditionMulticastIpAddr                   IpAddress,
    alaQoSAppliedConditionMulticastIpAddrStatus             INTEGER,
    alaQoSAppliedConditionMulticastIpMask                   IpAddress,
    alaQoSAppliedConditionMulticastNetworkGroup             SnmpAdminString,
    alaQoSAppliedConditionMulticastNetworkGroupStatus       INTEGER,
    alaQoSAppliedConditionTos                               Integer32,
    alaQoSAppliedConditionTosStatus                         INTEGER,
    alaQoSAppliedConditionTosMask                           Integer32,
    alaQoSAppliedConditionDscp                              Integer32,
    alaQoSAppliedConditionDscpStatus                        INTEGER,
    alaQoSAppliedConditionDscpMask                          Integer32,
    alaQoSAppliedConditionIpProtocol                        Integer32,
    alaQoSAppliedConditionIpProtocolStatus                  INTEGER,
    alaQoSAppliedConditionSourceIpPort                      Integer32,
    alaQoSAppliedConditionSourceIpPortStatus                INTEGER,
    alaQoSAppliedConditionDestinationIpPort                 Integer32,
    alaQoSAppliedConditionDestinationIpPortStatus           INTEGER,
    alaQoSAppliedConditionService                           SnmpAdminString,
    alaQoSAppliedConditionServiceStatus                     INTEGER,
    alaQoSAppliedConditionServiceGroup                      SnmpAdminString,
    alaQoSAppliedConditionServiceGroupStatus                INTEGER,
    alaQoSAppliedConditionIcmpType                          Integer32,
    alaQoSAppliedConditionIcmpTypeStatus                    INTEGER,
    alaQoSAppliedConditionIcmpCode                          Integer32,
    alaQoSAppliedConditionIcmpCodeStatus                    INTEGER,
    alaQoSAppliedConditionRowStatus                         RowStatus,
    alaQoSAppliedConditionSourcePortEnd                     Integer32,
    alaQoSAppliedConditionDestinationPortEnd                Integer32,
    alaQoSAppliedConditionSourceIpPortEnd                   Integer32,
    alaQoSAppliedConditionDestinationIpPortEnd              Integer32,
    alaQoSAppliedConditionSourceTcpPort                     Integer32,
    alaQoSAppliedConditionSourceTcpPortStatus               INTEGER,
    alaQoSAppliedConditionSourceTcpPortEnd                  Integer32,
    alaQoSAppliedConditionDestinationTcpPort                Integer32,
    alaQoSAppliedConditionDestinationTcpPortStatus          INTEGER,
    alaQoSAppliedConditionDestinationTcpPortEnd             Integer32,
    alaQoSAppliedConditionSourceUdpPort                     Integer32,
    alaQoSAppliedConditionSourceUdpPortStatus               INTEGER,
    alaQoSAppliedConditionSourceUdpPortEnd                  Integer32,
    alaQoSAppliedConditionDestinationUdpPort                Integer32,
    alaQoSAppliedConditionDestinationUdpPortStatus          INTEGER,
    alaQoSAppliedConditionDestinationUdpPortEnd             Integer32,
    alaQoSAppliedConditionEthertype                         Integer32,
    alaQoSAppliedConditionEthertypeStatus                   INTEGER,
    alaQoSAppliedConditionTcpFlags                          INTEGER,
    alaQoSAppliedConditionTcpFlagsStatus                    INTEGER,
    alaQoSAppliedConditionTcpFlagsVal                       Integer32,
    alaQoSAppliedConditionTcpFlagsValStatus                 INTEGER,
    alaQoSAppliedConditionTcpFlagsMask                      Integer32,
    alaQoSAppliedConditionTcpFlagsMaskStatus                INTEGER,
    alaQoSAppliedConditionTcpEstablished                    INTEGER,
    alaQoSAppliedConditionSourceIpv6Addr                    Ipv6Address,
    alaQoSAppliedConditionSourceIpv6AddrStatus              INTEGER,
    alaQoSAppliedConditionSourceIpv6Mask                    Ipv6Address,
    alaQoSAppliedConditionDestinationIpv6Addr               Ipv6Address,
    alaQoSAppliedConditionDestinationIpv6AddrStatus         INTEGER,
    alaQoSAppliedConditionDestinationIpv6Mask               Ipv6Address,
    alaQoSAppliedConditionIpv6Traffic                       INTEGER,
    alaQoSAppliedConditionIpv6NH                            Integer32,
    alaQoSAppliedConditionIpv6NHStatus                      INTEGER,
    alaQoSAppliedConditionIpv6FlowLabel                     Integer32,
    alaQoSAppliedConditionIpv6FlowLabelStatus               INTEGER,
    alaQoSAppliedConditionMcastIpv6Addr                     Ipv6Address,
    alaQoSAppliedConditionMcastIpv6AddrStatus               INTEGER,
    alaQoSAppliedConditionMcastIpv6Mask                     Ipv6Address,
    alaQoSAppliedConditionDscpEnd                           Integer32,
    alaQoSAppliedConditionInnerSourceVlan                   Integer32,
    alaQoSAppliedConditionInnerSourceVlanStatus             INTEGER,
    alaQoSAppliedConditionInner8021p                        Integer32,
    alaQoSAppliedConditionInner8021pStatus                  INTEGER,
    alaQoSAppliedConditionVrfName                           SnmpAdminString,
    alaQoSAppliedConditionVrfNameStatus                     INTEGER,
    alaQoSAppliedConditionFragments                         INTEGER
  }

alaQoSAppliedConditionName OBJECT-TYPE
  SYNTAX      SnmpAdminString (SIZE(0..31))
  MAX-ACCESS  not-accessible
  STATUS      current
  DESCRIPTION "Name of condition"
  ::= { alaQoSAppliedConditionEntry 1 }

alaQoSAppliedConditionSource OBJECT-TYPE
  SYNTAX      INTEGER {
                ldap (1),
                cli (2),
                blt (3),
                api (4),
                imp (5)
              }
  MAX-ACCESS  read-only
  STATUS      current
  DESCRIPTION "What entity created the condition."
  ::= { alaQoSAppliedConditionEntry 2 }

alaQoSAppliedConditionSourceSlot OBJECT-TYPE
  SYNTAX      Integer32 (0..16)
  MAX-ACCESS  read-only
  STATUS      current
  DESCRIPTION "Source physical slot used for traffic classification
               When 0, the port identifies an aggregate"
  ::= { alaQoSAppliedConditionEntry 3 }

alaQoSAppliedConditionSourceSlotStatus OBJECT-TYPE
  SYNTAX      INTEGER {
                enabled (1),
                disabled (2)
              }
  MAX-ACCESS  read-only
  STATUS      current
  DESCRIPTION "Status field indicating whether the source physical slot and
               port range needs to be matched(enabled) or not(disabled)."
  ::= { alaQoSAppliedConditionEntry 4 }

alaQoSAppliedConditionSourcePort OBJECT-TYPE
  SYNTAX      Integer32 (1..52)
  MAX-ACCESS  read-only
  STATUS      current
  DESCRIPTION "Source physical port range start to use for
               traffic classification"
  ::= { alaQoSAppliedConditionEntry 5 }

alaQoSAppliedConditionSourcePortGroup OBJECT-TYPE
  SYNTAX      SnmpAdminString (SIZE(0..31))
  MAX-ACCESS  read-only
  STATUS      current
  DESCRIPTION "Source physical port group to use for traffic classification"
  ::= { alaQoSAppliedConditionEntry 6 }

alaQoSAppliedConditionSourcePortGroupStatus OBJECT-TYPE
  SYNTAX      INTEGER {
                enabled (1),
                disabled (2)
              }
  MAX-ACCESS  read-only
  STATUS      current
  DESCRIPTION "Status field indicating whether the source physical port group
               needs to be matched(enabled) or not(disabled)."
  ::= { alaQoSAppliedConditionEntry 7 }

alaQoSAppliedConditionDestinationSlot OBJECT-TYPE
  SYNTAX      Integer32 (0..16)
  MAX-ACCESS  read-only
  STATUS      current
  DESCRIPTION "Destination physical slot used for traffic classification
               When 0, the port identifies an aggregate"
  ::= { alaQoSAppliedConditionEntry 8 }

alaQoSAppliedConditionDestinationSlotStatus OBJECT-TYPE
  SYNTAX      INTEGER {
                enabled (1),
                disabled (2)
              }
  MAX-ACCESS  read-only
  STATUS      current
  DESCRIPTION "Status field indicating whether the destination physical slot
               and port range needs to be matched(enabled) or not(disabled)."
  ::= { alaQoSAppliedConditionEntry 9 }

alaQoSAppliedConditionDestinationPort OBJECT-TYPE
  SYNTAX      Integer32 (1..52)
  MAX-ACCESS  read-only
  STATUS      current
  DESCRIPTION "Destination physical port range start to use for traffic
               classification"
  ::= { alaQoSAppliedConditionEntry 10 }

alaQoSAppliedConditionDestinationPortGroup OBJECT-TYPE
  SYNTAX      SnmpAdminString (SIZE(0..31))
  MAX-ACCESS  read-only
  STATUS      current
  DESCRIPTION "Destination physical port group to use for traffic
               classification"
  ::= { alaQoSAppliedConditionEntry 11 }

alaQoSAppliedConditionDestinationPortGroupStatus OBJECT-TYPE
  SYNTAX      INTEGER {
                enabled (1),
                disabled (2)
              }
  MAX-ACCESS  read-only
  STATUS      current
  DESCRIPTION "Status field indicating whether the destination physical port
               group needs to be matched(enabled) or not(disabled)."
  ::= { alaQoSAppliedConditionEntry 12 }


alaQoSAppliedConditionSourceMacAddr OBJECT-TYPE
  SYNTAX      MacAddress
  MAX-ACCESS  read-only
  STATUS      current
  DESCRIPTION "Source MAC address to use for traffic classification"
  ::= { alaQoSAppliedConditionEntry 13 }

alaQoSAppliedConditionSourceMacAddrStatus OBJECT-TYPE
  SYNTAX      INTEGER {
                enabled (1),
                disabled (2)
              }
  MAX-ACCESS  read-only
  STATUS      current
  DESCRIPTION "Status field indicating whether the source MAC address & mask
               needs to be matched(enabled) or not(disabled)."
  ::= { alaQoSAppliedConditionEntry 14 }

alaQoSAppliedConditionSourceMacMask OBJECT-TYPE
  SYNTAX      MacAddress
  MAX-ACCESS  read-only
  STATUS      current
  DESCRIPTION "Source MAC mask to use for traffic classification"
  ::= { alaQoSAppliedConditionEntry 15 }

alaQoSAppliedConditionSourceMacGroup OBJECT-TYPE
  SYNTAX      SnmpAdminString (SIZE(0..31))
  MAX-ACCESS  read-only
  STATUS      current
  DESCRIPTION "Source MAC group to use for traffic classification"
  ::= { alaQoSAppliedConditionEntry 16 }

alaQoSAppliedConditionSourceMacGroupStatus OBJECT-TYPE
  SYNTAX      INTEGER {
                enabled (1),
                disabled (2)
              }
  MAX-ACCESS  read-only
  STATUS      current
  DESCRIPTION "Status field indicating whether the source MAC group
               needs to be matched(enabled) or not(disabled)."
  ::= { alaQoSAppliedConditionEntry 17 }

alaQoSAppliedConditionDestinationMacAddr OBJECT-TYPE
  SYNTAX      MacAddress
  MAX-ACCESS  read-only
  STATUS      current
  DESCRIPTION "Destination MAC address to use for traffic classification"
  ::= { alaQoSAppliedConditionEntry 18 }

alaQoSAppliedConditionDestinationMacAddrStatus OBJECT-TYPE
  SYNTAX      INTEGER {
                enabled (1),
                disabled (2)
              }
  MAX-ACCESS  read-only
  STATUS      current
  DESCRIPTION "Status field indicating whether the destination MAC address
               & mask needs to be matched(enabled) or not(disabled)."
  ::= { alaQoSAppliedConditionEntry 19 }

alaQoSAppliedConditionDestinationMacMask OBJECT-TYPE
  SYNTAX      MacAddress
  MAX-ACCESS  read-only
  STATUS      current
  DESCRIPTION "Destination MAC mask to use for traffic classification"
  ::= { alaQoSAppliedConditionEntry 20 }

alaQoSAppliedConditionDestinationMacGroup OBJECT-TYPE
  SYNTAX      SnmpAdminString (SIZE(0..31))
  MAX-ACCESS  read-only
  STATUS      current
  DESCRIPTION "Destination MAC group to use for traffic classification"
  ::= { alaQoSAppliedConditionEntry 21 }

alaQoSAppliedConditionDestinationMacGroupStatus OBJECT-TYPE
  SYNTAX      INTEGER {
                enabled (1),
                disabled (2)
              }
  MAX-ACCESS  read-only
  STATUS      current
  DESCRIPTION "Status field indicating whether the destination MAC group
               needs to be matched(enabled) or not(disabled)."
  ::= { alaQoSAppliedConditionEntry 22 }

alaQoSAppliedConditionSourceVlan OBJECT-TYPE
  SYNTAX      Integer32 (0..4095)
  MAX-ACCESS  read-only
  STATUS      current
  DESCRIPTION "Source VLAN to use for traffic classification"
  ::= { alaQoSAppliedConditionEntry 23 }

alaQoSAppliedConditionSourceVlanStatus OBJECT-TYPE
  SYNTAX      INTEGER {
                enabled (1),
                disabled (2)
              }
  MAX-ACCESS  read-only
  STATUS      current
  DESCRIPTION "Status field indicating whether the source VLAN
               needs to be matched(enabled) or not(disabled)."
  ::= { alaQoSAppliedConditionEntry 24 }

alaQoSAppliedConditionDestinationVlan OBJECT-TYPE
  SYNTAX      Integer32 (0..4095)
  MAX-ACCESS  read-only
  STATUS      current
  DESCRIPTION "Destination VLAN to use for traffic classification"
  ::= { alaQoSAppliedConditionEntry 25 }

alaQoSAppliedConditionDestinationVlanStatus OBJECT-TYPE
  SYNTAX      INTEGER {
                enabled (1),
                disabled (2)
              }
  MAX-ACCESS  read-only
  STATUS      current
  DESCRIPTION "Status field indicating whether the destination VLAN
               needs to be matched(enabled) or not(disabled)."
  ::= { alaQoSAppliedConditionEntry 26 }

alaQoSAppliedCondition8021p OBJECT-TYPE
  SYNTAX      Integer32 (0..7)
  MAX-ACCESS  read-only
  STATUS      current
  DESCRIPTION "802.1p value to use for traffic classification"
  ::= { alaQoSAppliedConditionEntry 27 }

alaQoSAppliedCondition8021pStatus OBJECT-TYPE
  SYNTAX      INTEGER {
                enabled (1),
                disabled (2)
              }
  MAX-ACCESS  read-only
  STATUS      current
  DESCRIPTION "Status field indicating whether the 802.1p value
               needs to be matched(enabled) or not(disabled)."
  ::= { alaQoSAppliedConditionEntry 28 }

alaQoSAppliedConditionSourceIpAddr OBJECT-TYPE
  SYNTAX      IpAddress
  MAX-ACCESS  read-only
  STATUS      current
  DESCRIPTION "Source IP address to use for traffic classification"
  ::= { alaQoSAppliedConditionEntry 29 }

alaQoSAppliedConditionSourceIpAddrStatus OBJECT-TYPE
  SYNTAX      INTEGER {
                enabled (1),
                disabled (2)
              }
  MAX-ACCESS  read-only
  STATUS      current
  DESCRIPTION "Status field indicating whether the source IP address & mask
               needs to be matched(enabled) or not(disabled)."
  ::= { alaQoSAppliedConditionEntry 30 }

alaQoSAppliedConditionSourceIpMask OBJECT-TYPE
  SYNTAX      IpAddress
  MAX-ACCESS  read-only
  STATUS      current
  DESCRIPTION "Source IP mask to use for traffic classification"
  ::= { alaQoSAppliedConditionEntry 31 }

alaQoSAppliedConditionSourceNetworkGroup OBJECT-TYPE
  SYNTAX      SnmpAdminString (SIZE(0..31))
  MAX-ACCESS  read-only
  STATUS      current
  DESCRIPTION "Source network group to use for traffic classification"
  ::= { alaQoSAppliedConditionEntry 32 }

alaQoSAppliedConditionSourceNetworkGroupStatus OBJECT-TYPE
  SYNTAX      INTEGER {
                enabled (1),
                disabled (2)
              }
  MAX-ACCESS  read-only
  STATUS      current
  DESCRIPTION "Status field indicating whether the source network group
               needs to be matched(enabled) or not(disabled)."
  ::= { alaQoSAppliedConditionEntry 33 }

alaQoSAppliedConditionDestinationIpAddr OBJECT-TYPE
  SYNTAX      IpAddress
  MAX-ACCESS  read-only
  STATUS      current
  DESCRIPTION "Destination IP address to use for traffic classification"
  ::= { alaQoSAppliedConditionEntry 34 }

alaQoSAppliedConditionDestinationIpAddrStatus OBJECT-TYPE
  SYNTAX      INTEGER {
                enabled (1),
                disabled (2)
              }
  MAX-ACCESS  read-only
  STATUS      current
  DESCRIPTION "Status field indicating whether the destination IP address
               & mask needs to be matched(enabled) or not(disabled)."
  ::= { alaQoSAppliedConditionEntry 35 }

alaQoSAppliedConditionDestinationIpMask OBJECT-TYPE
  SYNTAX      IpAddress
  MAX-ACCESS  read-only
  STATUS      current
  DESCRIPTION "Destination IP mask to use for traffic classification"
  ::= { alaQoSAppliedConditionEntry 36 }

alaQoSAppliedConditionDestinationNetworkGroup OBJECT-TYPE
  SYNTAX      SnmpAdminString (SIZE(0..31))
  MAX-ACCESS  read-only
  STATUS      current
  DESCRIPTION "Destination network group to use for traffic classification"
  ::= { alaQoSAppliedConditionEntry 37 }

alaQoSAppliedConditionDestinationNetworkGroupStatus OBJECT-TYPE
  SYNTAX      INTEGER {
                enabled (1),
                disabled (2)
              }
  MAX-ACCESS  read-only
  STATUS      current
  DESCRIPTION "Status field indicating whether the destination network group
               needs to be matched(enabled) or not(disabled)."
  ::= { alaQoSAppliedConditionEntry 38 }

alaQoSAppliedConditionMulticastIpAddr OBJECT-TYPE
  SYNTAX      IpAddress
  MAX-ACCESS  read-only
  STATUS      current
  DESCRIPTION "Multicast IP address to use for traffic classification"
  ::= { alaQoSAppliedConditionEntry 39 }

alaQoSAppliedConditionMulticastIpAddrStatus OBJECT-TYPE
  SYNTAX      INTEGER {
                enabled (1),
                disabled (2)
              }
  MAX-ACCESS  read-only
  STATUS      current
  DESCRIPTION "Status field indicating whether the multicast IP address & mask
               needs to be matched(enabled) or not(disabled)."
  ::= { alaQoSAppliedConditionEntry 40 }

alaQoSAppliedConditionMulticastIpMask OBJECT-TYPE
  SYNTAX      IpAddress
  MAX-ACCESS  read-only
  STATUS      current
  DESCRIPTION "Multicast IP mask to use for traffic classification"
  ::= { alaQoSAppliedConditionEntry 41 }

alaQoSAppliedConditionMulticastNetworkGroup OBJECT-TYPE
  SYNTAX      SnmpAdminString (SIZE(0..31))
  MAX-ACCESS  read-only
  STATUS      current
  DESCRIPTION "Multicast network group to use for traffic classification"
  ::= { alaQoSAppliedConditionEntry 42 }

alaQoSAppliedConditionMulticastNetworkGroupStatus OBJECT-TYPE
  SYNTAX      INTEGER {
                enabled (1),
                disabled (2)
              }
  MAX-ACCESS  read-only
  STATUS      current
  DESCRIPTION "Status field indicating whether the multicast network group
               needs to be matched(enabled) or not(disabled)."
  ::= { alaQoSAppliedConditionEntry 43 }

alaQoSAppliedConditionTos OBJECT-TYPE
  SYNTAX      Integer32 (0..7)
  MAX-ACCESS  read-only
  STATUS      current
  DESCRIPTION "TOS value to use for traffic classification"
  ::= { alaQoSAppliedConditionEntry 44 }

alaQoSAppliedConditionTosStatus OBJECT-TYPE
  SYNTAX      INTEGER {
                enabled (1),
                disabled (2)
              }
  MAX-ACCESS  read-only
  STATUS      current
  DESCRIPTION "Status field indicating whether the TOS value & mask
               needs to be matched(enabled) or not(disabled)."
  ::= { alaQoSAppliedConditionEntry 45 }

alaQoSAppliedConditionTosMask OBJECT-TYPE
  SYNTAX      Integer32 (0..7)
  MAX-ACCESS  read-only
  STATUS      current
  DESCRIPTION "TOS mask to use for traffic classification"
  ::= { alaQoSAppliedConditionEntry 46 }

alaQoSAppliedConditionDscp OBJECT-TYPE
  SYNTAX      Integer32 (0..63)
  MAX-ACCESS  read-only
  STATUS      current
  DESCRIPTION "DSCP value to use for traffic classification"
  ::= { alaQoSAppliedConditionEntry 47 }

alaQoSAppliedConditionDscpStatus OBJECT-TYPE
  SYNTAX      INTEGER {
                enabled (1),
                disabled (2)
              }
  MAX-ACCESS  read-only
  STATUS      current
  DESCRIPTION "Status field indicating whether the DSCP value & mask
               needs to be matched(enabled) or not(disabled)."
  ::= { alaQoSAppliedConditionEntry 48 }

alaQoSAppliedConditionDscpMask OBJECT-TYPE
  SYNTAX      Integer32 (0..63)
  MAX-ACCESS  read-only
  STATUS      current
  DESCRIPTION "DSCP mask to use for traffic classification"
  ::= { alaQoSAppliedConditionEntry 49 }

alaQoSAppliedConditionIpProtocol OBJECT-TYPE
  SYNTAX      Integer32 (0..255)
  MAX-ACCESS  read-only
  STATUS      current
  DESCRIPTION "IP protocol to use for traffic classification."
  ::= { alaQoSAppliedConditionEntry 50 }

alaQoSAppliedConditionIpProtocolStatus OBJECT-TYPE
  SYNTAX      INTEGER {
                enabled (1),
                disabled (2)
              }
  MAX-ACCESS  read-only
  STATUS      current
  DESCRIPTION "Status field indicating whether the IP protocol
               needs to be matched(enabled) or not(disabled)."
  ::= { alaQoSAppliedConditionEntry 51 }

alaQoSAppliedConditionSourceIpPort OBJECT-TYPE
  SYNTAX      Integer32 (0..65535)
  MAX-ACCESS  read-only
  STATUS      current
  DESCRIPTION "Source IP port range start to use for traffic classification."
  ::= { alaQoSAppliedConditionEntry 52 }

alaQoSAppliedConditionSourceIpPortStatus OBJECT-TYPE
  SYNTAX      INTEGER {
                enabled (1),
                disabled (2)
              }
  MAX-ACCESS  read-only
  STATUS      current
  DESCRIPTION "Status field indicating whether the source IP port range
               needs to be matched(enabled) or not(disabled)."
  ::= { alaQoSAppliedConditionEntry 53 }

alaQoSAppliedConditionDestinationIpPort OBJECT-TYPE
  SYNTAX      Integer32 (0..65535)
  MAX-ACCESS  read-only
  STATUS      current
  DESCRIPTION "Destination IP port range start to use for traffic
               classification."
  ::= { alaQoSAppliedConditionEntry 54 }

alaQoSAppliedConditionDestinationIpPortStatus OBJECT-TYPE
  SYNTAX      INTEGER {
                enabled (1),
                disabled (2)
              }
  MAX-ACCESS  read-only
  STATUS      current
  DESCRIPTION "Status field indicating whether the destination IP port range
               needs to be matched(enabled) or not(disabled)."
  ::= { alaQoSAppliedConditionEntry 55 }

alaQoSAppliedConditionService OBJECT-TYPE
  SYNTAX      SnmpAdminString (SIZE(0..31))
  MAX-ACCESS  read-only
  STATUS      current
  DESCRIPTION "Name of service to use for traffic classification"
  ::= { alaQoSAppliedConditionEntry 56 }

alaQoSAppliedConditionServiceStatus OBJECT-TYPE
  SYNTAX      INTEGER {
                enabled (1),
                disabled (2)
              }
  MAX-ACCESS  read-only
  STATUS      current
  DESCRIPTION "Status field indicating whether the service
               needs to be matched(enabled) or not(disabled)."
  ::= { alaQoSAppliedConditionEntry 57 }

alaQoSAppliedConditionServiceGroup OBJECT-TYPE
  SYNTAX      SnmpAdminString (SIZE(0..31))
  MAX-ACCESS  read-only
  STATUS      current
  DESCRIPTION "Name of service group to use for traffic classification"
  ::= { alaQoSAppliedConditionEntry 58 }

alaQoSAppliedConditionServiceGroupStatus OBJECT-TYPE
  SYNTAX      INTEGER {
                enabled (1),
                disabled (2)
              }
  MAX-ACCESS  read-only
  STATUS      current
  DESCRIPTION "Status field indicating whether the service group
               needs to be matched(enabled) or not(disabled)."
  ::= { alaQoSAppliedConditionEntry 59 }

alaQoSAppliedConditionIcmpType OBJECT-TYPE
  SYNTAX      Integer32 (0..255)
  MAX-ACCESS  read-only
  STATUS      current
  DESCRIPTION "ICMP type to use for traffic classification"
  ::= { alaQoSAppliedConditionEntry 60 }

alaQoSAppliedConditionIcmpTypeStatus OBJECT-TYPE
  SYNTAX      INTEGER {
                enabled (1),
                disabled (2)
              }
  MAX-ACCESS  read-only
  STATUS      current
  DESCRIPTION "Status field indicating whether the ICMP type
               needs to be matched(enabled) or not(disabled)."
  ::= { alaQoSAppliedConditionEntry 61 }

alaQoSAppliedConditionIcmpCode OBJECT-TYPE
  SYNTAX      Integer32 (0..255)
  MAX-ACCESS  read-only
  STATUS      current
  DESCRIPTION "ICMP code to use for traffic classification"
  ::= { alaQoSAppliedConditionEntry 62 }

alaQoSAppliedConditionIcmpCodeStatus OBJECT-TYPE
  SYNTAX      INTEGER {
                enabled (1),
                disabled (2)
              }
  MAX-ACCESS  read-only
  STATUS      current
  DESCRIPTION "Status field indicating whether the ICMP code
               needs to be matched(enabled) or not(disabled)."
  ::= { alaQoSAppliedConditionEntry 63 }

alaQoSAppliedConditionRowStatus OBJECT-TYPE
  SYNTAX      RowStatus
  MAX-ACCESS  read-only
  STATUS      current
  DESCRIPTION "Used to create/delete conditions according to the
               RowStatus convention"
  ::= { alaQoSAppliedConditionEntry 64 }

alaQoSAppliedConditionSourcePortEnd OBJECT-TYPE
  SYNTAX      Integer32 (1..52)
  MAX-ACCESS  read-only
  STATUS      current
  DESCRIPTION "Source physical port range end to use for traffic
               classification.  Must be greater than port range start to
               indicate a range.  When '1', use source port as a single port."
  ::= { alaQoSAppliedConditionEntry 65 }

alaQoSAppliedConditionDestinationPortEnd OBJECT-TYPE
  SYNTAX      Integer32 (1..52)
  MAX-ACCESS  read-only
  STATUS      current
  DESCRIPTION "Destination physical port range end to use for traffic
               classification.  Must be greater than port range start to
               indicate a range.  When '1', use destination port as a single
               port."
  ::= { alaQoSAppliedConditionEntry 66 }

alaQoSAppliedConditionSourceIpPortEnd OBJECT-TYPE
  SYNTAX      Integer32 (0..65535)
  MAX-ACCESS  read-only
  STATUS      current
  DESCRIPTION "Source IP port range end to use for traffic classification.
               Must be greater than source IP port range start to indicate a
               range.  When '0', use source IP port as a single IP port."
  ::= { alaQoSAppliedConditionEntry 67 }

alaQoSAppliedConditionDestinationIpPortEnd OBJECT-TYPE
  SYNTAX      Integer32 (0..65535)
  MAX-ACCESS  read-only
  STATUS      current
  DESCRIPTION "Destination IP port range end to use for traffic classification.
               Must be greater than destination IP port range start to indicate
               a range.  When '0', use destination IP port as a single IP port."
  ::= { alaQoSAppliedConditionEntry 68 }

alaQoSAppliedConditionSourceTcpPort OBJECT-TYPE
  SYNTAX      Integer32 (0..65535)
  MAX-ACCESS  read-only
  STATUS      current
  DESCRIPTION "Source TCP port range start to use for traffic classification."
  ::= { alaQoSAppliedConditionEntry 69 }

alaQoSAppliedConditionSourceTcpPortStatus OBJECT-TYPE
  SYNTAX      INTEGER {
                enabled (1),
                disabled (2)
              }
  MAX-ACCESS  read-only
  STATUS      current
  DESCRIPTION "Status field indicating whether the source TCP port range
               needs to be matched(enabled) or not(disabled)."
  ::= { alaQoSAppliedConditionEntry 70 }

alaQoSAppliedConditionSourceTcpPortEnd OBJECT-TYPE
  SYNTAX      Integer32 (0..65535)
  MAX-ACCESS  read-only
  STATUS      current
  DESCRIPTION "Source TCP port range end to use for traffic classification.
               Must be greater than source TCP port range start to indicate a
               range.  When '0', use source TCP port as a single TCP port."
  ::= { alaQoSAppliedConditionEntry 71 }

alaQoSAppliedConditionDestinationTcpPort OBJECT-TYPE
  SYNTAX      Integer32 (0..65535)
  MAX-ACCESS  read-only
  STATUS      current
  DESCRIPTION "Destination TCP port range start to use for traffic
               classification."
  ::= { alaQoSAppliedConditionEntry 72 }

alaQoSAppliedConditionDestinationTcpPortStatus OBJECT-TYPE
  SYNTAX      INTEGER {
                enabled (1),
                disabled (2)
              }
  MAX-ACCESS  read-only
  STATUS      current
  DESCRIPTION "Status field indicating whether the destination TCP port range
               needs to be matched(enabled) or not(disabled)."
  ::= { alaQoSAppliedConditionEntry 73 }

alaQoSAppliedConditionDestinationTcpPortEnd OBJECT-TYPE
  SYNTAX      Integer32 (0..65535)
  MAX-ACCESS  read-only
  STATUS      current
  DESCRIPTION "Destination TCP port range end to use for traffic
               classification.  Must be greater than destination TCP port range
               start to indicate a range.  When '0', use destination TCP port
               as a single TCP port."
  ::= { alaQoSAppliedConditionEntry 74 }

alaQoSAppliedConditionSourceUdpPort OBJECT-TYPE
  SYNTAX      Integer32 (0..65535)
  MAX-ACCESS  read-only
  STATUS      current
  DESCRIPTION "Source UDP port range start to use for traffic classification."
  ::= { alaQoSAppliedConditionEntry 75 }

alaQoSAppliedConditionSourceUdpPortStatus OBJECT-TYPE
  SYNTAX      INTEGER {
                enabled (1),
                disabled (2)
              }
  MAX-ACCESS  read-only
  STATUS      current
  DESCRIPTION "Status field indicating whether the source UDP port range
               needs to be matched(enabled) or not(disabled)."
  ::= { alaQoSAppliedConditionEntry 76 }

alaQoSAppliedConditionSourceUdpPortEnd OBJECT-TYPE
  SYNTAX      Integer32 (0..65535)
  MAX-ACCESS  read-only
  STATUS      current
  DESCRIPTION "Source UDP port range end to use for traffic classification.
               Must be greater than source UDP port range start to indicate
               a range.  When '0', use source UDP port as a single UDP port."
  ::= { alaQoSAppliedConditionEntry 77 }

alaQoSAppliedConditionDestinationUdpPort OBJECT-TYPE
  SYNTAX      Integer32 (0..65535)
  MAX-ACCESS  read-only
  STATUS      current
  DESCRIPTION "Destination UDP port range start to use for traffic
               classification."
  ::= { alaQoSAppliedConditionEntry 78 }

alaQoSAppliedConditionDestinationUdpPortStatus OBJECT-TYPE
  SYNTAX      INTEGER {
                enabled (1),
                disabled (2)
              }
  MAX-ACCESS  read-only
  STATUS      current
  DESCRIPTION "Status field indicating whether the destination UDP port range
               needs to be matched(enabled) or not(disabled)."
  ::= { alaQoSAppliedConditionEntry 79 }

alaQoSAppliedConditionDestinationUdpPortEnd OBJECT-TYPE
  SYNTAX      Integer32 (0..65535)
  MAX-ACCESS  read-only
  STATUS      current
  DESCRIPTION "Destination UDP port range end to use for traffic
               classification.  Must be greater than destination UDP port range
               start to indicate a range.  When '0', use destination UDP port
               as a single TCP port."
  ::= { alaQoSAppliedConditionEntry 80 }

alaQoSAppliedConditionEthertype OBJECT-TYPE
  SYNTAX      Integer32 (0..65535)
  MAX-ACCESS  read-only
  STATUS      current
  DESCRIPTION "Ethertype value to use for traffic classification"
  ::= { alaQoSAppliedConditionEntry 81 }

alaQoSAppliedConditionEthertypeStatus OBJECT-TYPE
  SYNTAX      INTEGER {
                enabled (1),
                disabled (2)
              }
  MAX-ACCESS  read-only
  STATUS      current
  DESCRIPTION "Status field indicating whether the ethertype value
               needs to be matched(enabled) or not(disabled)."
  ::= { alaQoSAppliedConditionEntry 82 }

alaQoSAppliedConditionTcpFlags OBJECT-TYPE
  SYNTAX      INTEGER {
                all (1),
                any (2)
              }
  MAX-ACCESS  read-only
  STATUS      current
  DESCRIPTION "Use any/all specifieid TCP flags for traffic classification"
  ::= { alaQoSAppliedConditionEntry 83 }

alaQoSAppliedConditionTcpFlagsStatus OBJECT-TYPE
  SYNTAX      INTEGER {
                enabled (1),
                disabled (2)
              }
  MAX-ACCESS  read-only
  STATUS      current
  DESCRIPTION "Status field indicating whether the TCP flag bits
               needs to be matched(enabled) or not(disabled)."
  ::= { alaQoSAppliedConditionEntry 84 }

alaQoSAppliedConditionTcpFlagsVal OBJECT-TYPE
  SYNTAX      Integer32
  MAX-ACCESS  read-only
  STATUS      current
  DESCRIPTION "TCP flags values used for traffic classification"
  ::= { alaQoSAppliedConditionEntry 85 }

alaQoSAppliedConditionTcpFlagsValStatus OBJECT-TYPE
  SYNTAX      INTEGER {
                enabled (1),
                disabled (2)
              }
  MAX-ACCESS  read-only
  STATUS      current
  DESCRIPTION "Not used"
  ::= { alaQoSAppliedConditionEntry 86 }

alaQoSAppliedConditionTcpFlagsMask OBJECT-TYPE
  SYNTAX      Integer32
  MAX-ACCESS  read-only
  STATUS      current
  DESCRIPTION "Mask of TCP flags bits used for traffic classification"
  ::= { alaQoSAppliedConditionEntry 87 }

alaQoSAppliedConditionTcpFlagsMaskStatus OBJECT-TYPE
  SYNTAX      INTEGER {
                enabled (1),
                disabled (2)
              }
  MAX-ACCESS  read-only
  STATUS      current
  DESCRIPTION "Not used"
  ::= { alaQoSAppliedConditionEntry 88 }

alaQoSAppliedConditionTcpEstablished OBJECT-TYPE
  SYNTAX      INTEGER {
                yes (1),
                no (2)
              }
  MAX-ACCESS  read-only
  STATUS      current
  DESCRIPTION "Look for established TCP sessions in classification"
  ::= { alaQoSAppliedConditionEntry 89 }

alaQoSAppliedConditionSourceIpv6Addr OBJECT-TYPE
  SYNTAX      Ipv6Address
  MAX-ACCESS  read-only
  STATUS      current
  DESCRIPTION "Source IPv6 address to use for traffic classification"
  ::= { alaQoSAppliedConditionEntry 90 }

alaQoSAppliedConditionSourceIpv6AddrStatus OBJECT-TYPE
  SYNTAX      INTEGER {
                enabled (1),
                disabled (2)
              }
  MAX-ACCESS  read-only
  STATUS      current
  DESCRIPTION "Status field indicating whether the source IPv6 address & mask
               needs to be matched(enabled) or not(disabled)."
  ::= { alaQoSAppliedConditionEntry 91 }

alaQoSAppliedConditionSourceIpv6Mask OBJECT-TYPE
  SYNTAX      Ipv6Address
  MAX-ACCESS  read-only
  STATUS      current
  DESCRIPTION "Source IPv6 mask to use for traffic classification"
  ::= { alaQoSAppliedConditionEntry 92 }

alaQoSAppliedConditionDestinationIpv6Addr OBJECT-TYPE
  SYNTAX      Ipv6Address
  MAX-ACCESS  read-only
  STATUS      current
  DESCRIPTION "Destination IPv6 address to use for traffic classification"
  ::= { alaQoSAppliedConditionEntry 93 }

alaQoSAppliedConditionDestinationIpv6AddrStatus OBJECT-TYPE
  SYNTAX      INTEGER {
                enabled (1),
                disabled (2)
              }
  MAX-ACCESS  read-only
  STATUS      current
  DESCRIPTION "Status field indicating whether the destination IPv6 address & mask
               needs to be matched(enabled) or not(disabled)."
  ::= { alaQoSAppliedConditionEntry 94 }

alaQoSAppliedConditionDestinationIpv6Mask OBJECT-TYPE
  SYNTAX      Ipv6Address
  MAX-ACCESS  read-only
  STATUS      current
  DESCRIPTION "Destination IPv6 mask to use for traffic classification"
  ::= { alaQoSAppliedConditionEntry 95 }

alaQoSAppliedConditionIpv6Traffic OBJECT-TYPE
  SYNTAX      INTEGER {
                yes (1),
                no (2)
              }
  MAX-ACCESS  read-only
  STATUS      current
  DESCRIPTION "classify IPV6 traffic "
  ::= { alaQoSAppliedConditionEntry 96 }

alaQoSAppliedConditionIpv6NH OBJECT-TYPE
  SYNTAX      Integer32 (0..255)
  MAX-ACCESS  read-only
  STATUS      current
  DESCRIPTION "NH value to use for traffic classification"
  DEFVAL      { 0 }
  ::= { alaQoSAppliedConditionEntry 97 }

alaQoSAppliedConditionIpv6NHStatus OBJECT-TYPE
  SYNTAX      INTEGER {
                enabled (1),
                disabled (2)
              }
  MAX-ACCESS  read-only
  STATUS      current
  DESCRIPTION "Status field indicating whether the NH value
               needs to be matched(enabled) or not(disabled)."
  DEFVAL      { disabled }
  ::= { alaQoSAppliedConditionEntry 98 }

alaQoSAppliedConditionIpv6FlowLabel OBJECT-TYPE
  SYNTAX      Integer32 (0..1048575)
  MAX-ACCESS  read-only
  STATUS      current
  DESCRIPTION "FL value to use for traffic classification"
  DEFVAL      { 0 }
  ::= { alaQoSAppliedConditionEntry 99 }

alaQoSAppliedConditionIpv6FlowLabelStatus OBJECT-TYPE
  SYNTAX      INTEGER {
                enabled (1),
                disabled (2)
              }
  MAX-ACCESS  read-only
  STATUS      current
  DESCRIPTION "Status field indicating whether the flow label value
               needs to be matched(enabled) or not(disabled)."
  DEFVAL      { disabled }
  ::= { alaQoSAppliedConditionEntry 100 }

alaQoSAppliedConditionMcastIpv6Addr OBJECT-TYPE
  SYNTAX      Ipv6Address
  MAX-ACCESS  read-create
  STATUS      current
  DESCRIPTION "Multicast IPv6 address to use for traffic classification"
  DEFVAL      { '00000000000000000000000000000000'h }
  ::= { alaQoSAppliedConditionEntry 101 }

alaQoSAppliedConditionMcastIpv6AddrStatus OBJECT-TYPE
  SYNTAX      INTEGER {
                enabled (1),
                disabled (2)
              }
  MAX-ACCESS  read-create
  STATUS      current
  DESCRIPTION "Status field indicating whether the multicast IPv6 address & mask
               needs to be matched(enabled) or not(disabled)."
  DEFVAL      { disabled }
  ::= { alaQoSAppliedConditionEntry 102 }

alaQoSAppliedConditionMcastIpv6Mask OBJECT-TYPE
  SYNTAX      Ipv6Address
  MAX-ACCESS  read-create
  STATUS      current
  DESCRIPTION "Multicast IPv6 mask to use for traffic classification"
  DEFVAL      { 'ffffffffffffffffffffffffffffffff'h }
  ::= { alaQoSAppliedConditionEntry 103 }

alaQoSAppliedConditionDscpEnd OBJECT-TYPE
  SYNTAX      Integer32 (0..63)
  MAX-ACCESS  read-only
  STATUS      current
  DESCRIPTION "DSCP value to use for traffic classification"
  ::= { alaQoSAppliedConditionEntry 104 }

alaQoSAppliedConditionInnerSourceVlan OBJECT-TYPE
  SYNTAX      Integer32 (0..4095)
  MAX-ACCESS  read-only
  STATUS      current
  DESCRIPTION "Customer VLAN to use for traffic classification"
  DEFVAL      { 0 }
  ::= { alaQoSAppliedConditionEntry 105 }

alaQoSAppliedConditionInnerSourceVlanStatus OBJECT-TYPE
  SYNTAX      INTEGER {
                enabled (1),
                disabled (2)
              }
  MAX-ACCESS  read-only
  STATUS      current
  DESCRIPTION "Status field indicating whether the inner VLAN
               needs to be matched(enabled) or not(disabled)."
  DEFVAL      { disabled }
  ::= { alaQoSAppliedConditionEntry 106 }

alaQoSAppliedConditionInner8021p OBJECT-TYPE
  SYNTAX      Integer32 (0..7)
  MAX-ACCESS  read-only
  STATUS      current
  DESCRIPTION "Customer 802.1p to use for traffic classification"
  DEFVAL      { 0 }
  ::= { alaQoSAppliedConditionEntry 107 }

alaQoSAppliedConditionInner8021pStatus OBJECT-TYPE
  SYNTAX      INTEGER {
                enabled (1),
                disabled (2)
              }
  MAX-ACCESS  read-only
  STATUS      current
  DESCRIPTION "Status field indicating whether the inner 802.1p
               needs to be matched(enabled) or not(disabled)."
  DEFVAL      { disabled }
  ::= { alaQoSAppliedConditionEntry 108}

alaQoSAppliedConditionVrfName OBJECT-TYPE
  SYNTAX      SnmpAdminString (SIZE(0..31))
  MAX-ACCESS  read-create
  STATUS      current
  DESCRIPTION "Name of Vrf to match traffic in"
  ::= { alaQoSAppliedConditionEntry 109 }

alaQoSAppliedConditionVrfNameStatus OBJECT-TYPE
  SYNTAX      INTEGER {
                enabled (1),
                disabled (2)
              }
  MAX-ACCESS  read-create
  STATUS      current
  DESCRIPTION "Status field indicating whether the traffic from a specific vrf               needs to be matched(enabled) or not(disabled)."
  DEFVAL      { disabled }
  ::= { alaQoSAppliedConditionEntry 110 }

alaQoSAppliedConditionFragments OBJECT-TYPE
  SYNTAX      INTEGER {
                yes (1),
                no (2)
              }
  MAX-ACCESS  read-only
  STATUS      current
  DESCRIPTION "TCP packet fragments"
  DEFVAL      { no }
  ::= { alaQoSAppliedConditionEntry 111 }

--
-- Definition of service table
--

alaQoSServiceTable OBJECT-TYPE
  SYNTAX      SEQUENCE OF QoSServiceEntry
  MAX-ACCESS  not-accessible
  STATUS      current
  DESCRIPTION "Table of QoS Service definitions"
  ::= { alaQoSMIBObjects 5 }

alaQoSServiceEntry OBJECT-TYPE
  SYNTAX      QoSServiceEntry
  MAX-ACCESS  not-accessible
  STATUS      current
  DESCRIPTION "Definition of QoS Service"
  INDEX {
          alaQoSServiceName
        }
  ::= { alaQoSServiceTable 1 }

QoSServiceEntry ::=
  SEQUENCE
  {
    alaQoSServiceName                                       SnmpAdminString,
    alaQoSServiceSource                                     INTEGER,
    alaQoSServiceProtocol                                   Integer32,
    alaQoSServiceSourceIpPort                               Integer32,
    alaQoSServiceSourceIpPortStatus                         INTEGER,
    alaQoSServiceDestinationIpPort                          Integer32,
    alaQoSServiceDestinationIpPortStatus                    INTEGER,
    alaQoSServiceRowStatus                                  RowStatus,
    alaQoSServiceSourceIpPortEnd                            Integer32,
    alaQoSServiceDestinationIpPortEnd                       Integer32,
    alaQoSServiceSourceTcpPort                              Integer32,
    alaQoSServiceSourceTcpPortStatus                        INTEGER,
    alaQoSServiceSourceTcpPortEnd                           Integer32,
    alaQoSServiceDestinationTcpPort                         Integer32,
    alaQoSServiceDestinationTcpPortStatus                   INTEGER,
    alaQoSServiceDestinationTcpPortEnd                      Integer32,
    alaQoSServiceSourceUdpPort                              Integer32,
    alaQoSServiceSourceUdpPortStatus                        INTEGER,
    alaQoSServiceSourceUdpPortEnd                           Integer32,
    alaQoSServiceDestinationUdpPort                         Integer32,
    alaQoSServiceDestinationUdpPortStatus                   INTEGER,
    alaQoSServiceDestinationUdpPortEnd                      Integer32
  }

alaQoSServiceName OBJECT-TYPE
  SYNTAX      SnmpAdminString (SIZE(0..31))
  MAX-ACCESS  not-accessible
  STATUS      current
  DESCRIPTION "Name of the service"
  ::= { alaQoSServiceEntry 1 }

alaQoSServiceSource OBJECT-TYPE
  SYNTAX      INTEGER {
                ldap (1),
                cli (2),
                blt (3),
                api (4),
                imp (5)
              }
  MAX-ACCESS  read-create
  STATUS      current
  DESCRIPTION "What entity created the service."
  DEFVAL      { cli }
  ::= { alaQoSServiceEntry 2 }

alaQoSServiceProtocol OBJECT-TYPE
  SYNTAX      Integer32 (0..255)
  MAX-ACCESS  read-create
  STATUS      current
  DESCRIPTION "protocol field for Service"
  DEFVAL      { 0 }
  ::= { alaQoSServiceEntry 3 }

alaQoSServiceSourceIpPort OBJECT-TYPE
  SYNTAX      Integer32 (0..65535)
  MAX-ACCESS  read-create
  STATUS      current
  DESCRIPTION "Source IP port range start to use for traffic classification."
  ::= { alaQoSServiceEntry 4 }

alaQoSServiceSourceIpPortStatus OBJECT-TYPE
  SYNTAX      INTEGER {
                enabled (1),
                disabled (2)
              }
  MAX-ACCESS  read-create
  STATUS      current
  DESCRIPTION "Status field indicating whether the source IP port range
               needs to be matched(enabled) or not(disabled)."
  DEFVAL      { disabled }
  ::= { alaQoSServiceEntry 5 }

alaQoSServiceDestinationIpPort OBJECT-TYPE
  SYNTAX      Integer32 (0..65535)
  MAX-ACCESS  read-create
  STATUS      current
  DESCRIPTION "Destination IP port range start to use for traffic
               classification."
  ::= { alaQoSServiceEntry 6 }

alaQoSServiceDestinationIpPortStatus OBJECT-TYPE
  SYNTAX      INTEGER {
                enabled (1),
                disabled (2)
              }
  MAX-ACCESS  read-create
  STATUS      current
  DESCRIPTION "Status field indicating whether the destination IP port range
               needs to be matched(enabled) or not(disabled)."
  DEFVAL      { disabled }
  ::= { alaQoSServiceEntry 7 }

alaQoSServiceRowStatus OBJECT-TYPE
  SYNTAX      RowStatus
  MAX-ACCESS  read-create
  STATUS      current
  DESCRIPTION "Used to create/delete services according to the
               RowStatus convention"
  ::= { alaQoSServiceEntry 8 }

alaQoSServiceSourceIpPortEnd OBJECT-TYPE
  SYNTAX      Integer32 (0..65535)
  MAX-ACCESS  read-create
  STATUS      current
  DESCRIPTION "Source IP port range end to use for traffic classification.
               Must be greater than source IP port range start to indicate
               a range.  When '0', use source IP port as a single IP port."
  ::= { alaQoSServiceEntry 9 }

alaQoSServiceDestinationIpPortEnd OBJECT-TYPE
  SYNTAX      Integer32 (0..65535)
  MAX-ACCESS  read-create
  STATUS      current
  DESCRIPTION "Destination IP port range end to use for traffic classification.
               Must be greater than destination IP port range start to indicate
               a range.  When '0', use destination IP port as a single IP port."
  ::= { alaQoSServiceEntry 10 }

alaQoSServiceSourceTcpPort OBJECT-TYPE
  SYNTAX      Integer32 (0..65535)
  MAX-ACCESS  read-create
  STATUS      current
  DESCRIPTION "Source TCP port range start to use for traffic classification."
  ::= { alaQoSServiceEntry 11 }

alaQoSServiceSourceTcpPortStatus OBJECT-TYPE
  SYNTAX      INTEGER {
                enabled (1),
                disabled (2)
              }
  MAX-ACCESS  read-create
  STATUS      current
  DESCRIPTION "Status field indicating whether the source TCP port range
               needs to be matched(enabled) or not(disabled)."
  DEFVAL      { disabled }
  ::= { alaQoSServiceEntry 12 }

alaQoSServiceSourceTcpPortEnd OBJECT-TYPE
  SYNTAX      Integer32 (0..65535)
  MAX-ACCESS  read-create
  STATUS      current
  DESCRIPTION "Source TCP port range end to use for traffic classification.
               Must be greater than source TCP port range start to indicate a
               range.  When '0', use source TCP port as a single TCP port."
  ::= { alaQoSServiceEntry 13 }

alaQoSServiceDestinationTcpPort OBJECT-TYPE
  SYNTAX      Integer32 (0..65535)
  MAX-ACCESS  read-create
  STATUS      current
  DESCRIPTION "Destination TCP port range start to use for traffic
               classification."
  ::= { alaQoSServiceEntry 14 }

alaQoSServiceDestinationTcpPortStatus OBJECT-TYPE
  SYNTAX      INTEGER {
                enabled (1),
                disabled (2)
              }
  MAX-ACCESS  read-create
  STATUS      current
  DESCRIPTION "Status field indicating whether the destination TCP port range
               needs to be matched(enabled) or not(disabled)."
  DEFVAL      { disabled }
  ::= { alaQoSServiceEntry 15 }

alaQoSServiceDestinationTcpPortEnd OBJECT-TYPE
  SYNTAX      Integer32 (0..65535)
  MAX-ACCESS  read-create
  STATUS      current
  DESCRIPTION "Destination TCP port range end to use for traffic
               classification.  Must be greater than destination TCP port range
               start to indicate a range.  When '0', use destination TCP port as
               a single TCP port."
  ::= { alaQoSServiceEntry 16 }

alaQoSServiceSourceUdpPort OBJECT-TYPE
  SYNTAX      Integer32 (0..65535)
  MAX-ACCESS  read-create
  STATUS      current
  DESCRIPTION "Source UDP port range start to use for traffic classification."
  ::= { alaQoSServiceEntry 17 }

alaQoSServiceSourceUdpPortStatus OBJECT-TYPE
  SYNTAX      INTEGER {
                enabled (1),
                disabled (2)
              }
  MAX-ACCESS  read-create
  STATUS      current
  DESCRIPTION "Status field indicating whether the source UDP port range
               needs to be matched(enabled) or not(disabled)."
  DEFVAL      { disabled }
  ::= { alaQoSServiceEntry 18 }

alaQoSServiceSourceUdpPortEnd OBJECT-TYPE
  SYNTAX      Integer32 (0..65535)
  MAX-ACCESS  read-create
  STATUS      current
  DESCRIPTION "Source UDP port range end to use for traffic classification.
               Must be greater than source UDP port range start to indicate a
               range.  When '0', use source UDP port as a single UDP port."
  ::= { alaQoSServiceEntry 19 }

alaQoSServiceDestinationUdpPort OBJECT-TYPE
  SYNTAX      Integer32 (0..65535)
  MAX-ACCESS  read-create
  STATUS      current
  DESCRIPTION "Destination UDP port range start to use for traffic
               classification."
  ::= { alaQoSServiceEntry 20 }

alaQoSServiceDestinationUdpPortStatus OBJECT-TYPE
  SYNTAX      INTEGER {
                enabled (1),
                disabled (2)
              }
  MAX-ACCESS  read-create
  STATUS      current
  DESCRIPTION "Status field indicating whether the destination UDP port range
               needs to be matched(enabled) or not(disabled)."
  DEFVAL      { disabled }
  ::= { alaQoSServiceEntry 21 }

alaQoSServiceDestinationUdpPortEnd OBJECT-TYPE
  SYNTAX      Integer32 (0..65535)
  MAX-ACCESS  read-create
  STATUS      current
  DESCRIPTION "Destination UDP port range end to use for traffic
               classification.  Must be greater than destination UDP port range
               start to indicate a range.  When '0', use destination UDP port as
               a single UDP port."
  ::= { alaQoSServiceEntry 22 }


--
-- Definition of service table
--

alaQoSAppliedServiceTable OBJECT-TYPE
  SYNTAX      SEQUENCE OF QoSAppliedServiceEntry
  MAX-ACCESS  not-accessible
  STATUS      current
  DESCRIPTION "Table of QoS AppliedService definitions"
  ::= { alaQoSMIBObjects 6 }

alaQoSAppliedServiceEntry OBJECT-TYPE
  SYNTAX      QoSAppliedServiceEntry
  MAX-ACCESS  not-accessible
  STATUS      current
  DESCRIPTION "Definition of QoS AppliedService"
  INDEX {
          alaQoSAppliedServiceName
        }
  ::= { alaQoSAppliedServiceTable 1 }

QoSAppliedServiceEntry ::=
  SEQUENCE
  {
    alaQoSAppliedServiceName                                SnmpAdminString,
    alaQoSAppliedServiceSource                              INTEGER,
    alaQoSAppliedServiceProtocol                            Integer32,
    alaQoSAppliedServiceSourceIpPort                        Integer32,
    alaQoSAppliedServiceSourceIpPortStatus                  INTEGER,
    alaQoSAppliedServiceDestinationIpPort                   Integer32,
    alaQoSAppliedServiceDestinationIpPortStatus             INTEGER,
    alaQoSAppliedServiceRowStatus                           RowStatus,
    alaQoSAppliedServiceSourceIpPortEnd                     Integer32,
    alaQoSAppliedServiceDestinationIpPortEnd                Integer32,
    alaQoSAppliedServiceSourceTcpPort                       Integer32,
    alaQoSAppliedServiceSourceTcpPortStatus                 INTEGER,
    alaQoSAppliedServiceSourceTcpPortEnd                    Integer32,
    alaQoSAppliedServiceDestinationTcpPort                  Integer32,
    alaQoSAppliedServiceDestinationTcpPortStatus            INTEGER,
    alaQoSAppliedServiceDestinationTcpPortEnd               Integer32,
    alaQoSAppliedServiceSourceUdpPort                       Integer32,
    alaQoSAppliedServiceSourceUdpPortStatus                 INTEGER,
    alaQoSAppliedServiceSourceUdpPortEnd                    Integer32,
    alaQoSAppliedServiceDestinationUdpPort                  Integer32,
    alaQoSAppliedServiceDestinationUdpPortStatus            INTEGER,
    alaQoSAppliedServiceDestinationUdpPortEnd               Integer32
  }

alaQoSAppliedServiceName OBJECT-TYPE
  SYNTAX      SnmpAdminString (SIZE(0..31))
  MAX-ACCESS  not-accessible
  STATUS      current
  DESCRIPTION "Name of the service"
  ::= { alaQoSAppliedServiceEntry 1 }

alaQoSAppliedServiceSource OBJECT-TYPE
  SYNTAX      INTEGER {
                ldap (1),
                cli (2),
                blt (3),
                api (4),
                imp (5)
              }
  MAX-ACCESS  read-only
  STATUS      current
  DESCRIPTION "What entity created the service."
  ::= { alaQoSAppliedServiceEntry 2 }

alaQoSAppliedServiceProtocol OBJECT-TYPE
  SYNTAX      Integer32 (0..255)
  MAX-ACCESS  read-only
  STATUS      current
  DESCRIPTION "protocol field for AppliedService"
  ::= { alaQoSAppliedServiceEntry 3 }

alaQoSAppliedServiceSourceIpPort OBJECT-TYPE
  SYNTAX      Integer32 (0..65535)
  MAX-ACCESS  read-only
  STATUS      current
  DESCRIPTION "Source IP port range start to use for traffic classification."
  ::= { alaQoSAppliedServiceEntry 4 }

alaQoSAppliedServiceSourceIpPortStatus OBJECT-TYPE
  SYNTAX      INTEGER {
                enabled (1),
                disabled (2)
              }
  MAX-ACCESS  read-only
  STATUS      current
  DESCRIPTION "Status field indicating whether the source IP port range
               needs to be matched(enabled) or not(disabled)."
  ::= { alaQoSAppliedServiceEntry 5 }

alaQoSAppliedServiceDestinationIpPort OBJECT-TYPE
  SYNTAX      Integer32 (0..65535)
  MAX-ACCESS  read-only
  STATUS      current
  DESCRIPTION "Destination IP port range start to use for traffic
               classification."
  ::= { alaQoSAppliedServiceEntry 6 }

alaQoSAppliedServiceDestinationIpPortStatus OBJECT-TYPE
  SYNTAX      INTEGER {
                enabled (1),
                disabled (2)
              }
  MAX-ACCESS  read-only
  STATUS      current
  DESCRIPTION "Status field indicating whether the destination IP port range
               needs to be matched(enabled) or not(disabled)."
  ::= { alaQoSAppliedServiceEntry 7 }

alaQoSAppliedServiceRowStatus OBJECT-TYPE
  SYNTAX      RowStatus
  MAX-ACCESS  read-only
  STATUS      current
  DESCRIPTION "Used to create/delete services according to the
               RowStatus convention"
  ::= { alaQoSAppliedServiceEntry 8 }

alaQoSAppliedServiceSourceIpPortEnd OBJECT-TYPE
  SYNTAX      Integer32 (0..65535)
  MAX-ACCESS  read-only
  STATUS      current
  DESCRIPTION "Source IP port range end to use for traffic classification.
               Must be greater than source IP port range start to indicate
               a range.  When '0', use source IP port as a single IP port."
  ::= { alaQoSAppliedServiceEntry 9 }

alaQoSAppliedServiceDestinationIpPortEnd OBJECT-TYPE
  SYNTAX      Integer32 (0..65535)
  MAX-ACCESS  read-only
  STATUS      current
  DESCRIPTION "Destination IP port range end to use for traffic classification.
               Must be greater than destination IP port range start to indicate
               a range.  When '0', use destination IP port as a single IP port."
  ::= { alaQoSAppliedServiceEntry 10 }

alaQoSAppliedServiceSourceTcpPort OBJECT-TYPE
  SYNTAX      Integer32 (0..65535)
  MAX-ACCESS  read-only
  STATUS      current
  DESCRIPTION "Source TCP port range start to use for traffic classification."
  ::= { alaQoSAppliedServiceEntry 11 }

alaQoSAppliedServiceSourceTcpPortStatus OBJECT-TYPE
  SYNTAX      INTEGER {
                enabled (1),
                disabled (2)
              }
  MAX-ACCESS  read-only
  STATUS      current
  DESCRIPTION "Status field indicating whether the source TCP port range
               needs to be matched(enabled) or not(disabled)."
  ::= { alaQoSAppliedServiceEntry 12 }

alaQoSAppliedServiceSourceTcpPortEnd OBJECT-TYPE
  SYNTAX      Integer32 (0..65535)
  MAX-ACCESS  read-only
  STATUS      current
  DESCRIPTION "Source TCP port range end to use for traffic classification.
               Must be greater than source TCP port range start to indicate a
               range.  When '0', use source TCP port as a single TCP port."
  ::= { alaQoSAppliedServiceEntry 13 }

alaQoSAppliedServiceDestinationTcpPort OBJECT-TYPE
  SYNTAX      Integer32 (0..65535)
  MAX-ACCESS  read-only
  STATUS      current
  DESCRIPTION "Destination TCP port range start to use for traffic
               classification."
  ::= { alaQoSAppliedServiceEntry 14 }

alaQoSAppliedServiceDestinationTcpPortStatus OBJECT-TYPE
  SYNTAX      INTEGER {
                enabled (1),
                disabled (2)
              }
  MAX-ACCESS  read-only
  STATUS      current
  DESCRIPTION "Status field indicating whether the destination TCP port range
               needs to be matched(enabled) or not(disabled)."
  ::= { alaQoSAppliedServiceEntry 15 }

alaQoSAppliedServiceDestinationTcpPortEnd OBJECT-TYPE
  SYNTAX      Integer32 (0..65535)
  MAX-ACCESS  read-only
  STATUS      current
  DESCRIPTION "Destination TCP port range end to use for traffic
               classification.  Must be greater than destination TCP port range
               start to indicate a range.  When '0', use destination TCP port as
               a single TCP port."
  ::= { alaQoSAppliedServiceEntry 16 }

alaQoSAppliedServiceSourceUdpPort OBJECT-TYPE
  SYNTAX      Integer32 (0..65535)
  MAX-ACCESS  read-only
  STATUS      current
  DESCRIPTION "Source UDP port range start to use for traffic classification."
  ::= { alaQoSAppliedServiceEntry 17 }

alaQoSAppliedServiceSourceUdpPortStatus OBJECT-TYPE
  SYNTAX      INTEGER {
                enabled (1),
                disabled (2)
              }
  MAX-ACCESS  read-only
  STATUS      current
  DESCRIPTION "Status field indicating whether the source UDP port range
               needs to be matched(enabled) or not(disabled)."
  ::= { alaQoSAppliedServiceEntry 18 }

alaQoSAppliedServiceSourceUdpPortEnd OBJECT-TYPE
  SYNTAX      Integer32 (0..65535)
  MAX-ACCESS  read-only
  STATUS      current
  DESCRIPTION "Source UDP port range end to use for traffic classification.
               Must be greater than source UDP port range start to indicate a
               range.  When '0', use source UDP port as a single UDP port."
  ::= { alaQoSAppliedServiceEntry 19 }

alaQoSAppliedServiceDestinationUdpPort OBJECT-TYPE
  SYNTAX      Integer32 (0..65535)
  MAX-ACCESS  read-only
  STATUS      current
  DESCRIPTION "Destination UDP port range start to use for traffic
               classification."
  ::= { alaQoSAppliedServiceEntry 20 }

alaQoSAppliedServiceDestinationUdpPortStatus OBJECT-TYPE
  SYNTAX      INTEGER {
                enabled (1),
                disabled (2)
              }
  MAX-ACCESS  read-only
  STATUS      current
  DESCRIPTION "Status field indicating whether the destination UDP port range
               needs to be matched(enabled) or not(disabled)."
  ::= { alaQoSAppliedServiceEntry 21 }

alaQoSAppliedServiceDestinationUdpPortEnd OBJECT-TYPE
  SYNTAX      Integer32 (0..65535)
  MAX-ACCESS  read-only
  STATUS      current
  DESCRIPTION "Destination UDP port range end to use for traffic
               classification.  Must be greater than destination UDP port range
               start to indicate a range.  When '0', use destination UDP port as
               a single UDP port."
  ::= { alaQoSAppliedServiceEntry 22 }


--
-- Definition of service group table
--

alaQoSServiceGroupsTable OBJECT-TYPE
  SYNTAX      SEQUENCE OF QoSServiceGroupsEntry
  MAX-ACCESS  not-accessible
  STATUS      current
  DESCRIPTION "Table of QoS ServiceGroups definitions"
  ::= { alaQoSMIBObjects 7 }

alaQoSServiceGroupsEntry OBJECT-TYPE
  SYNTAX      QoSServiceGroupsEntry
  MAX-ACCESS  not-accessible
  STATUS      current
  DESCRIPTION "Definition of QoS ServiceGroups"
  INDEX {
          alaQoSServiceGroupsName
        }
  ::= { alaQoSServiceGroupsTable 1 }

QoSServiceGroupsEntry ::=
  SEQUENCE
  {
    alaQoSServiceGroupsName                                 SnmpAdminString,
    alaQoSServiceGroupsSource                               INTEGER,
    alaQoSServiceGroupsStatus                               RowStatus
  }

alaQoSServiceGroupsName OBJECT-TYPE
  SYNTAX      SnmpAdminString (SIZE(0..31))
  MAX-ACCESS  not-accessible
  STATUS      current
  DESCRIPTION "Name of service group"
  ::= { alaQoSServiceGroupsEntry 1 }

alaQoSServiceGroupsSource OBJECT-TYPE
  SYNTAX      INTEGER {
                ldap (1),
                cli (2),
                blt (3),
                api (4),
                imp (5)
              }
  MAX-ACCESS  read-create
  STATUS      current
  DESCRIPTION "What entity created the service group."
  DEFVAL      { cli }
  ::= { alaQoSServiceGroupsEntry 2 }

alaQoSServiceGroupsStatus OBJECT-TYPE
  SYNTAX      RowStatus
  MAX-ACCESS  read-create
  STATUS      current
  DESCRIPTION "Used to create/delete service groups according to the
               RowStatus convention"
  ::= { alaQoSServiceGroupsEntry 3 }


--
-- Definition of service group table
--

alaQoSAppliedServiceGroupsTable OBJECT-TYPE
  SYNTAX      SEQUENCE OF QoSAppliedServiceGroupsEntry
  MAX-ACCESS  not-accessible
  STATUS      current
  DESCRIPTION "Table of QoS AppliedServiceGroups definitions"
  ::= { alaQoSMIBObjects 8 }

alaQoSAppliedServiceGroupsEntry OBJECT-TYPE
  SYNTAX      QoSAppliedServiceGroupsEntry
  MAX-ACCESS  not-accessible
  STATUS      current
  DESCRIPTION "Definition of QoS AppliedServiceGroups"
  INDEX {
          alaQoSAppliedServiceGroupsName
        }
  ::= { alaQoSAppliedServiceGroupsTable 1 }

QoSAppliedServiceGroupsEntry ::=
  SEQUENCE
  {
    alaQoSAppliedServiceGroupsName                          SnmpAdminString,
    alaQoSAppliedServiceGroupsSource                        INTEGER,
    alaQoSAppliedServiceGroupsStatus                        RowStatus
  }

alaQoSAppliedServiceGroupsName OBJECT-TYPE
  SYNTAX      SnmpAdminString (SIZE(0..31))
  MAX-ACCESS  not-accessible
  STATUS      current
  DESCRIPTION "Name of service group"
  ::= { alaQoSAppliedServiceGroupsEntry 1 }

alaQoSAppliedServiceGroupsSource OBJECT-TYPE
  SYNTAX      INTEGER {
                ldap (1),
                cli (2),
                blt (3),
                api (4),
                imp (5)
              }
  MAX-ACCESS  read-only
  STATUS      current
  DESCRIPTION "What entity created the service group."
  ::= { alaQoSAppliedServiceGroupsEntry 2 }

alaQoSAppliedServiceGroupsStatus OBJECT-TYPE
  SYNTAX      RowStatus
  MAX-ACCESS  read-only
  STATUS      current
  DESCRIPTION "Used to create/delete service groups according to the
               RowStatus convention"
  ::= { alaQoSAppliedServiceGroupsEntry 3 }


--
-- Definition of service group entry table
--

alaQoSServiceGroupTable OBJECT-TYPE
  SYNTAX      SEQUENCE OF QoSServiceGroupEntry
  MAX-ACCESS  not-accessible
  STATUS      current
  DESCRIPTION "Table of QoS ServiceGroup definitions"
  ::= { alaQoSMIBObjects 9 }

alaQoSServiceGroupEntry OBJECT-TYPE
  SYNTAX      QoSServiceGroupEntry
  MAX-ACCESS  not-accessible
  STATUS      current
  DESCRIPTION "Definition of QoS ServiceGroup"
  INDEX {
          alaQoSServiceGroupsName,
          alaQoSServiceGroupServiceName
        }
  ::= { alaQoSServiceGroupTable 1 }

QoSServiceGroupEntry ::=
  SEQUENCE
  {
    alaQoSServiceGroupServiceName                           SnmpAdminString,
    alaQoSServiceGroupStatus                                RowStatus
  }

alaQoSServiceGroupServiceName OBJECT-TYPE
  SYNTAX      SnmpAdminString (SIZE(0..31))
  MAX-ACCESS  not-accessible
  STATUS      current
  DESCRIPTION "Name of service in service group entry"
  ::= { alaQoSServiceGroupEntry 1 }

alaQoSServiceGroupStatus OBJECT-TYPE
  SYNTAX      RowStatus
  MAX-ACCESS  read-create
  STATUS      current
  DESCRIPTION "Used to create/delete service group entries according to the
               RowStatus convention"
  ::= { alaQoSServiceGroupEntry 2 }


--
-- Definition of service group entry table
--

alaQoSAppliedServiceGroupTable OBJECT-TYPE
  SYNTAX      SEQUENCE OF QoSAppliedServiceGroupEntry
  MAX-ACCESS  not-accessible
  STATUS      current
  DESCRIPTION "Table of QoS AppliedServiceGroup definitions"
  ::= { alaQoSMIBObjects 10 }

alaQoSAppliedServiceGroupEntry OBJECT-TYPE
  SYNTAX      QoSAppliedServiceGroupEntry
  MAX-ACCESS  not-accessible
  STATUS      current
  DESCRIPTION "Definition of QoS AppliedServiceGroup"
  INDEX {
          alaQoSAppliedServiceGroupsName,
          alaQoSAppliedServiceGroupServiceName
        }
  ::= { alaQoSAppliedServiceGroupTable 1 }

QoSAppliedServiceGroupEntry ::=
  SEQUENCE
  {
    alaQoSAppliedServiceGroupServiceName                    SnmpAdminString,
    alaQoSAppliedServiceGroupStatus                         RowStatus
  }

alaQoSAppliedServiceGroupServiceName OBJECT-TYPE
  SYNTAX      SnmpAdminString (SIZE(0..31))
  MAX-ACCESS  not-accessible
  STATUS      current
  DESCRIPTION "Name of service in service group entry"
  ::= { alaQoSAppliedServiceGroupEntry 1 }

alaQoSAppliedServiceGroupStatus OBJECT-TYPE
  SYNTAX      RowStatus
  MAX-ACCESS  read-only
  STATUS      current
  DESCRIPTION "Used to create/delete service group entries according to the
               RowStatus convention"
  ::= { alaQoSAppliedServiceGroupEntry 2 }


--
-- Definition of network group table
--

alaQoSNetworkGroupsTable OBJECT-TYPE
  SYNTAX      SEQUENCE OF QoSNetworkGroupsEntry
  MAX-ACCESS  not-accessible
  STATUS      current
  DESCRIPTION "Table of QoS NetworkGroups definitions"
  ::= { alaQoSMIBObjects 11 }

alaQoSNetworkGroupsEntry OBJECT-TYPE
  SYNTAX      QoSNetworkGroupsEntry
  MAX-ACCESS  not-accessible
  STATUS      current
  DESCRIPTION "Definition of QoS NetworkGroups"
  INDEX {
          alaQoSNetworkGroupsName
        }
  ::= { alaQoSNetworkGroupsTable 1 }

QoSNetworkGroupsEntry ::=
  SEQUENCE
  {
    alaQoSNetworkGroupsName                                 SnmpAdminString,
    alaQoSNetworkGroupsSource                               INTEGER,
    alaQoSNetworkGroupsStatus                               RowStatus
  }

alaQoSNetworkGroupsName OBJECT-TYPE
  SYNTAX      SnmpAdminString (SIZE(0..31))
  MAX-ACCESS  not-accessible
  STATUS      current
  DESCRIPTION "Name of network group"
  ::= { alaQoSNetworkGroupsEntry 1 }

alaQoSNetworkGroupsSource OBJECT-TYPE
  SYNTAX      INTEGER {
                ldap (1),
                cli (2),
                blt (3),
                api (4),
                imp (5)
              }
  MAX-ACCESS  read-create
  STATUS      current
  DESCRIPTION "What entity created the network group."
  DEFVAL      { cli }
  ::= { alaQoSNetworkGroupsEntry 2 }

alaQoSNetworkGroupsStatus OBJECT-TYPE
  SYNTAX      RowStatus
  MAX-ACCESS  read-create
  STATUS      current
  DESCRIPTION "Used to create/delete network groups according to the
               RowStatus convention"
  ::= { alaQoSNetworkGroupsEntry 3 }


--
-- Definition of network group table
--

alaQoSAppliedNetworkGroupsTable OBJECT-TYPE
  SYNTAX      SEQUENCE OF QoSAppliedNetworkGroupsEntry
  MAX-ACCESS  not-accessible
  STATUS      current
  DESCRIPTION "Table of QoS AppliedNetworkGroups definitions"
  ::= { alaQoSMIBObjects 12 }

alaQoSAppliedNetworkGroupsEntry OBJECT-TYPE
  SYNTAX      QoSAppliedNetworkGroupsEntry
  MAX-ACCESS  not-accessible
  STATUS      current
  DESCRIPTION "Definition of QoS AppliedNetworkGroups"
  INDEX {
          alaQoSAppliedNetworkGroupsName
        }
  ::= { alaQoSAppliedNetworkGroupsTable 1 }

QoSAppliedNetworkGroupsEntry ::=
  SEQUENCE
  {
    alaQoSAppliedNetworkGroupsName                          SnmpAdminString,
    alaQoSAppliedNetworkGroupsSource                        INTEGER,
    alaQoSAppliedNetworkGroupsStatus                        RowStatus
  }

alaQoSAppliedNetworkGroupsName OBJECT-TYPE
  SYNTAX      SnmpAdminString (SIZE(0..31))
  MAX-ACCESS  not-accessible
  STATUS      current
  DESCRIPTION "Name of network group"
  ::= { alaQoSAppliedNetworkGroupsEntry 1 }

alaQoSAppliedNetworkGroupsSource OBJECT-TYPE
  SYNTAX      INTEGER {
                ldap (1),
                cli (2),
                blt (3),
                api (4),
                imp (5)
              }
  MAX-ACCESS  read-only
  STATUS      current
  DESCRIPTION "What entity created the network group."
  ::= { alaQoSAppliedNetworkGroupsEntry 2 }

alaQoSAppliedNetworkGroupsStatus OBJECT-TYPE
  SYNTAX      RowStatus
  MAX-ACCESS  read-only
  STATUS      current
  DESCRIPTION "Used to create/delete network groups according to the
               RowStatus convention"
  ::= { alaQoSAppliedNetworkGroupsEntry 3 }


--
-- Definition of network group entry table
--

alaQoSNetworkGroupTable OBJECT-TYPE
  SYNTAX      SEQUENCE OF QoSNetworkGroupEntry
  MAX-ACCESS  not-accessible
  STATUS      current
  DESCRIPTION "Table of QoS NetworkGroup definitions"
  ::= { alaQoSMIBObjects 13 }

alaQoSNetworkGroupEntry OBJECT-TYPE
  SYNTAX      QoSNetworkGroupEntry
  MAX-ACCESS  not-accessible
  STATUS      current
  DESCRIPTION "Definition of QoS NetworkGroup"
  INDEX {
          alaQoSNetworkGroupsName,
          alaQoSNetworkGroupIpAddr,
          alaQoSNetworkGroupIpMask
        }
  ::= { alaQoSNetworkGroupTable 1 }

QoSNetworkGroupEntry ::=
  SEQUENCE
  {
    alaQoSNetworkGroupIpAddr                                IpAddress,
    alaQoSNetworkGroupIpMask                                IpAddress,
    alaQoSNetworkGroupStatus                                RowStatus
  }

alaQoSNetworkGroupIpAddr OBJECT-TYPE
  SYNTAX      IpAddress
  MAX-ACCESS  not-accessible
  STATUS      current
  DESCRIPTION "IP address for network group entry."
  ::= { alaQoSNetworkGroupEntry 1 }

alaQoSNetworkGroupIpMask OBJECT-TYPE
  SYNTAX      IpAddress
  MAX-ACCESS  not-accessible
  STATUS      current
  DESCRIPTION "IP mask for network group entry."
  ::= { alaQoSNetworkGroupEntry 2 }

alaQoSNetworkGroupStatus OBJECT-TYPE
  SYNTAX      RowStatus
  MAX-ACCESS  read-create
  STATUS      current
  DESCRIPTION "Used to create/delete network group entries according to the
               RowStatus convention"
  ::= { alaQoSNetworkGroupEntry 3 }


--
-- Definition of network group entry table
--

alaQoSAppliedNetworkGroupTable OBJECT-TYPE
  SYNTAX      SEQUENCE OF QoSAppliedNetworkGroupEntry
  MAX-ACCESS  not-accessible
  STATUS      current
  DESCRIPTION "Table of QoS AppliedNetworkGroup definitions"
  ::= { alaQoSMIBObjects 14 }

alaQoSAppliedNetworkGroupEntry OBJECT-TYPE
  SYNTAX      QoSAppliedNetworkGroupEntry
  MAX-ACCESS  not-accessible
  STATUS      current
  DESCRIPTION "Definition of QoS AppliedNetworkGroup"
  INDEX {
          alaQoSAppliedNetworkGroupsName,
          alaQoSAppliedNetworkGroupIpAddr,
          alaQoSAppliedNetworkGroupIpMask
        }
  ::= { alaQoSAppliedNetworkGroupTable 1 }

QoSAppliedNetworkGroupEntry ::=
  SEQUENCE
  {
    alaQoSAppliedNetworkGroupIpAddr                         IpAddress,
    alaQoSAppliedNetworkGroupIpMask                         IpAddress,
    alaQoSAppliedNetworkGroupStatus                         RowStatus
  }

alaQoSAppliedNetworkGroupIpAddr OBJECT-TYPE
  SYNTAX      IpAddress
  MAX-ACCESS  not-accessible
  STATUS      current
  DESCRIPTION "IP address for network group entry."
  ::= { alaQoSAppliedNetworkGroupEntry 1 }

alaQoSAppliedNetworkGroupIpMask OBJECT-TYPE
  SYNTAX      IpAddress
  MAX-ACCESS  not-accessible
  STATUS      current
  DESCRIPTION "IP mask for network group entry."
  ::= { alaQoSAppliedNetworkGroupEntry 2 }

alaQoSAppliedNetworkGroupStatus OBJECT-TYPE
  SYNTAX      RowStatus
  MAX-ACCESS  read-only
  STATUS      current
  DESCRIPTION "Used to create/delete network group entries according to the
               RowStatus convention"
  ::= { alaQoSAppliedNetworkGroupEntry 3 }


--
-- Definition of mac group table
--

alaQoSMACGroupsTable OBJECT-TYPE
  SYNTAX      SEQUENCE OF QoSMACGroupsEntry
  MAX-ACCESS  not-accessible
  STATUS      current
  DESCRIPTION "Table of QoS MACGroups definitions"
  ::= { alaQoSMIBObjects 15 }

alaQoSMACGroupsEntry OBJECT-TYPE
  SYNTAX      QoSMACGroupsEntry
  MAX-ACCESS  not-accessible
  STATUS      current
  DESCRIPTION "Definition of QoS MACGroups"
  INDEX {
          alaQoSMACGroupsName
        }
  ::= { alaQoSMACGroupsTable 1 }

QoSMACGroupsEntry ::=
  SEQUENCE
  {
    alaQoSMACGroupsName                                     SnmpAdminString,
    alaQoSMACGroupsSource                                   INTEGER,
    alaQoSMACGroupsStatus                                   RowStatus
  }

alaQoSMACGroupsName OBJECT-TYPE
  SYNTAX      SnmpAdminString (SIZE(0..31))
  MAX-ACCESS  not-accessible
  STATUS      current
  DESCRIPTION "Name of MAC group"
  ::= { alaQoSMACGroupsEntry 1 }

alaQoSMACGroupsSource OBJECT-TYPE
  SYNTAX      INTEGER {
                ldap (1),
                cli (2),
                blt (3),
                api (4),
                imp (5)
              }
  MAX-ACCESS  read-create
  STATUS      current
  DESCRIPTION "What entity created the MAC group."
  DEFVAL      { cli }
  ::= { alaQoSMACGroupsEntry 2 }

alaQoSMACGroupsStatus OBJECT-TYPE
  SYNTAX      RowStatus
  MAX-ACCESS  read-create
  STATUS      current
  DESCRIPTION "Used to create/delete MAC groups according to the
               RowStatus convention"
  ::= { alaQoSMACGroupsEntry 3 }


--
-- Definition of mac group table
--

alaQoSAppliedMACGroupsTable OBJECT-TYPE
  SYNTAX      SEQUENCE OF QoSAppliedMACGroupsEntry
  MAX-ACCESS  not-accessible
  STATUS      current
  DESCRIPTION "Table of QoS AppliedMACGroups definitions"
  ::= { alaQoSMIBObjects 16 }

alaQoSAppliedMACGroupsEntry OBJECT-TYPE
  SYNTAX      QoSAppliedMACGroupsEntry
  MAX-ACCESS  not-accessible
  STATUS      current
  DESCRIPTION "Definition of QoS AppliedMACGroups"
  INDEX {
          alaQoSAppliedMACGroupsName
        }
  ::= { alaQoSAppliedMACGroupsTable 1 }

QoSAppliedMACGroupsEntry ::=
  SEQUENCE
  {
    alaQoSAppliedMACGroupsName                              SnmpAdminString,
    alaQoSAppliedMACGroupsSource                            INTEGER,
    alaQoSAppliedMACGroupsStatus                            RowStatus
  }

alaQoSAppliedMACGroupsName OBJECT-TYPE
  SYNTAX      SnmpAdminString (SIZE(0..31))
  MAX-ACCESS  not-accessible
  STATUS      current
  DESCRIPTION "Name of MAC group"
  ::= { alaQoSAppliedMACGroupsEntry 1 }

alaQoSAppliedMACGroupsSource OBJECT-TYPE
  SYNTAX      INTEGER {
                ldap (1),
                cli (2),
                blt (3),
                api (4),
                imp (5)
              }
  MAX-ACCESS  read-only
  STATUS      current
  DESCRIPTION "What entity created the MAC group."
  ::= { alaQoSAppliedMACGroupsEntry 2 }

alaQoSAppliedMACGroupsStatus OBJECT-TYPE
  SYNTAX      RowStatus
  MAX-ACCESS  read-only
  STATUS      current
  DESCRIPTION "Used to create/delete MAC groups according to the
               RowStatus convention"
  ::= { alaQoSAppliedMACGroupsEntry 3 }


--
-- Definition of MAC group entry table
--

alaQoSMACGroupTable OBJECT-TYPE
  SYNTAX      SEQUENCE OF QoSMACGroupEntry
  MAX-ACCESS  not-accessible
  STATUS      current
  DESCRIPTION "Table of QoS MACGroup definitions"
  ::= { alaQoSMIBObjects 17 }

alaQoSMACGroupEntry OBJECT-TYPE
  SYNTAX      QoSMACGroupEntry
  MAX-ACCESS  not-accessible
  STATUS      current
  DESCRIPTION "Definition of QoS MACGroup"
  INDEX {
          alaQoSMACGroupsName,
          alaQoSMACGroupMacAddr,
          alaQoSMACGroupMacMask
        }
  ::= { alaQoSMACGroupTable 1 }

QoSMACGroupEntry ::=
  SEQUENCE
  {
    alaQoSMACGroupMacAddr                                   MacAddress,
    alaQoSMACGroupMacMask                                   MacAddress,
    alaQoSMACGroupStatus                                    RowStatus
  }

alaQoSMACGroupMacAddr OBJECT-TYPE
  SYNTAX      MacAddress
  MAX-ACCESS  not-accessible
  STATUS      current
  DESCRIPTION "MAC address for MAC group entry"
  ::= { alaQoSMACGroupEntry 1 }

alaQoSMACGroupMacMask OBJECT-TYPE
  SYNTAX      MacAddress
  MAX-ACCESS  not-accessible
  STATUS      current
  DESCRIPTION "MAC mask for MAC group entry"
  ::= { alaQoSMACGroupEntry 2 }

alaQoSMACGroupStatus OBJECT-TYPE
  SYNTAX      RowStatus
  MAX-ACCESS  read-create
  STATUS      current
  DESCRIPTION "Used to create/delete MAC group entries according to the
               RowStatus convention"
  ::= { alaQoSMACGroupEntry 3 }


--
-- Definition of MAC group entry table
--

alaQoSAppliedMACGroupTable OBJECT-TYPE
  SYNTAX      SEQUENCE OF QoSAppliedMACGroupEntry
  MAX-ACCESS  not-accessible
  STATUS      current
  DESCRIPTION "Table of QoS AppliedMACGroup definitions"
  ::= { alaQoSMIBObjects 18 }

alaQoSAppliedMACGroupEntry OBJECT-TYPE
  SYNTAX      QoSAppliedMACGroupEntry
  MAX-ACCESS  not-accessible
  STATUS      current
  DESCRIPTION "Definition of QoS AppliedMACGroup"
  INDEX {
          alaQoSAppliedMACGroupsName,
          alaQoSAppliedMACGroupMacAddr,
          alaQoSAppliedMACGroupMacMask
        }
  ::= { alaQoSAppliedMACGroupTable 1 }

QoSAppliedMACGroupEntry ::=
  SEQUENCE
  {
    alaQoSAppliedMACGroupMacAddr                            MacAddress,
    alaQoSAppliedMACGroupMacMask                            MacAddress,
    alaQoSAppliedMACGroupStatus                             RowStatus
  }

alaQoSAppliedMACGroupMacAddr OBJECT-TYPE
  SYNTAX      MacAddress
  MAX-ACCESS  not-accessible
  STATUS      current
  DESCRIPTION "MAC address for MAC group entry"
  ::= { alaQoSAppliedMACGroupEntry 1 }

alaQoSAppliedMACGroupMacMask OBJECT-TYPE
  SYNTAX      MacAddress
  MAX-ACCESS  not-accessible
  STATUS      current
  DESCRIPTION "MAC mask for MAC group entry"
  ::= { alaQoSAppliedMACGroupEntry 2 }

alaQoSAppliedMACGroupStatus OBJECT-TYPE
  SYNTAX      RowStatus
  MAX-ACCESS  read-only
  STATUS      current
  DESCRIPTION "Used to create/delete MAC group entries according to the
               RowStatus convention"
  ::= { alaQoSAppliedMACGroupEntry 3 }


--
-- Definition of port group table
--

alaQoSPortGroupsTable OBJECT-TYPE
  SYNTAX      SEQUENCE OF QoSPortGroupsEntry
  MAX-ACCESS  not-accessible
  STATUS      current
  DESCRIPTION "Table of QoS PortGroups definitions"
  ::= { alaQoSMIBObjects 19 }

alaQoSPortGroupsEntry OBJECT-TYPE
  SYNTAX      QoSPortGroupsEntry
  MAX-ACCESS  not-accessible
  STATUS      current
  DESCRIPTION "Definition of QoS PortGroups"
  INDEX {
          alaQoSPortGroupsName
        }
  ::= { alaQoSPortGroupsTable 1 }

QoSPortGroupsEntry ::=
  SEQUENCE
  {
    alaQoSPortGroupsName                                    SnmpAdminString,
    alaQoSPortGroupsSource                                  INTEGER,
    alaQoSPortGroupsStatus                                  RowStatus
  }

alaQoSPortGroupsName OBJECT-TYPE
  SYNTAX      SnmpAdminString (SIZE(0..31))
  MAX-ACCESS  not-accessible
  STATUS      current
  DESCRIPTION "Name of port group"
  ::= { alaQoSPortGroupsEntry 1 }

alaQoSPortGroupsSource OBJECT-TYPE
  SYNTAX      INTEGER {
                ldap (1),
                cli (2),
                blt (3),
                api (4),
                imp (5)
              }
  MAX-ACCESS  read-create
  STATUS      current
  DESCRIPTION "What entity created the port group."
  DEFVAL      { cli }
  ::= { alaQoSPortGroupsEntry 2 }

alaQoSPortGroupsStatus OBJECT-TYPE
  SYNTAX      RowStatus
  MAX-ACCESS  read-create
  STATUS      current
  DESCRIPTION "Used to create/delete port groups according to the
               RowStatus convention"
  ::= { alaQoSPortGroupsEntry 3 }


--
-- Definition of port group table
--

alaQoSAppliedPortGroupsTable OBJECT-TYPE
  SYNTAX      SEQUENCE OF QoSAppliedPortGroupsEntry
  MAX-ACCESS  not-accessible
  STATUS      current
  DESCRIPTION "Table of QoS AppliedPortGroups definitions"
  ::= { alaQoSMIBObjects 20 }

alaQoSAppliedPortGroupsEntry OBJECT-TYPE
  SYNTAX      QoSAppliedPortGroupsEntry
  MAX-ACCESS  not-accessible
  STATUS      current
  DESCRIPTION "Definition of QoS AppliedPortGroups"
  INDEX {
          alaQoSAppliedPortGroupsName
        }
  ::= { alaQoSAppliedPortGroupsTable 1 }

QoSAppliedPortGroupsEntry ::=
  SEQUENCE
  {
    alaQoSAppliedPortGroupsName                             SnmpAdminString,
    alaQoSAppliedPortGroupsSource                           INTEGER,
    alaQoSAppliedPortGroupsStatus                           RowStatus
  }

alaQoSAppliedPortGroupsName OBJECT-TYPE
  SYNTAX      SnmpAdminString (SIZE(0..31))
  MAX-ACCESS  not-accessible
  STATUS      current
  DESCRIPTION "Name of port group"
  ::= { alaQoSAppliedPortGroupsEntry 1 }

alaQoSAppliedPortGroupsSource OBJECT-TYPE
  SYNTAX      INTEGER {
                ldap (1),
                cli (2),
                blt (3),
                api (4),
                imp (5)
              }
  MAX-ACCESS  read-only
  STATUS      current
  DESCRIPTION "What entity created the port group."
  ::= { alaQoSAppliedPortGroupsEntry 2 }

alaQoSAppliedPortGroupsStatus OBJECT-TYPE
  SYNTAX      RowStatus
  MAX-ACCESS  read-only
  STATUS      current
  DESCRIPTION "Used to create/delete port groups according to the
               RowStatus convention"
  ::= { alaQoSAppliedPortGroupsEntry 3 }


--
-- Definition of port group entry table
--

alaQoSPortGroupTable OBJECT-TYPE
  SYNTAX      SEQUENCE OF QoSPortGroupEntry
  MAX-ACCESS  not-accessible
  STATUS      current
  DESCRIPTION "Table of QoS PortGroup definitions"
  ::= { alaQoSMIBObjects 21 }

alaQoSPortGroupEntry OBJECT-TYPE
  SYNTAX      QoSPortGroupEntry
  MAX-ACCESS  not-accessible
  STATUS      current
  DESCRIPTION "Definition of QoS PortGroup"
  INDEX {
          alaQoSPortGroupsName,
          alaQoSPortGroupSlot,
          alaQoSPortGroupPort,
          alaQoSPortGroupPortEnd
        }
  ::= { alaQoSPortGroupTable 1 }

QoSPortGroupEntry ::=
  SEQUENCE
  {
    alaQoSPortGroupSlot                                     Integer32,
    alaQoSPortGroupPort                                     Integer32,
    alaQoSPortGroupStatus                                   RowStatus,
    alaQoSPortGroupPortEnd                                  Integer32
  }

alaQoSPortGroupSlot OBJECT-TYPE
  SYNTAX      Integer32 (1..16)
  MAX-ACCESS  not-accessible
  STATUS      current
  DESCRIPTION "Physical slot for port group entry"
  ::= { alaQoSPortGroupEntry 1 }

alaQoSPortGroupPort OBJECT-TYPE
  SYNTAX      Integer32 (1..52)
  MAX-ACCESS  not-accessible
  STATUS      current
  DESCRIPTION "Physical port range start for port group entry"
  ::= { alaQoSPortGroupEntry 2 }

alaQoSPortGroupStatus OBJECT-TYPE
  SYNTAX      RowStatus
  MAX-ACCESS  read-create
  STATUS      current
  DESCRIPTION "Used to create/delete port group entries according to the
               RowStatus convention"
  ::= { alaQoSPortGroupEntry 3 }

alaQoSPortGroupPortEnd OBJECT-TYPE
  SYNTAX      Integer32 (0..52)
  MAX-ACCESS  not-accessible
  STATUS      current
  DESCRIPTION "Physical port range end for port group entry
               Must be greater than port range start to indicate a range.
               When '1', use port as a single port."
  ::= { alaQoSPortGroupEntry 4 }


--
-- Definition of port group entry table
--

alaQoSAppliedPortGroupTable OBJECT-TYPE
  SYNTAX      SEQUENCE OF QoSAppliedPortGroupEntry
  MAX-ACCESS  not-accessible
  STATUS      current
  DESCRIPTION "Table of QoS AppliedPortGroup definitions"
  ::= { alaQoSMIBObjects 22 }

alaQoSAppliedPortGroupEntry OBJECT-TYPE
  SYNTAX      QoSAppliedPortGroupEntry
  MAX-ACCESS  not-accessible
  STATUS      current
  DESCRIPTION "Definition of QoS AppliedPortGroup"
  INDEX {
          alaQoSAppliedPortGroupsName,
          alaQoSAppliedPortGroupSlot,
          alaQoSAppliedPortGroupPort,
          alaQoSAppliedPortGroupPortEnd
        }
  ::= { alaQoSAppliedPortGroupTable 1 }

QoSAppliedPortGroupEntry ::=
  SEQUENCE
  {
    alaQoSAppliedPortGroupSlot                              Integer32,
    alaQoSAppliedPortGroupPort                              Integer32,
    alaQoSAppliedPortGroupStatus                            RowStatus,
    alaQoSAppliedPortGroupPortEnd                           Integer32
  }

alaQoSAppliedPortGroupSlot OBJECT-TYPE
  SYNTAX      Integer32 (1..16)
  MAX-ACCESS  not-accessible
  STATUS      current
  DESCRIPTION "Physical slot for port group entry"
  ::= { alaQoSAppliedPortGroupEntry 1 }

alaQoSAppliedPortGroupPort OBJECT-TYPE
  SYNTAX      Integer32 (1..52)
  MAX-ACCESS  not-accessible
  STATUS      current
  DESCRIPTION "Physical port range start for port group entry"
  ::= { alaQoSAppliedPortGroupEntry 2 }

alaQoSAppliedPortGroupStatus OBJECT-TYPE
  SYNTAX      RowStatus
  MAX-ACCESS  read-only
  STATUS      current
  DESCRIPTION "Used to create/delete port group entries according to the
               RowStatus convention"
  ::= { alaQoSAppliedPortGroupEntry 3 }

alaQoSAppliedPortGroupPortEnd OBJECT-TYPE
  SYNTAX      Integer32 (0..52)
  MAX-ACCESS  not-accessible
  STATUS      current
  DESCRIPTION "Physical port range end for port group entry
               Must be greater than port range start to indicate a range.
               When '1', use port as a single port."
  ::= { alaQoSAppliedPortGroupEntry 4 }


--
-- Definition of map group table
--

alaQoSMapGroupsTable OBJECT-TYPE
  SYNTAX      SEQUENCE OF QoSMapGroupsEntry
  MAX-ACCESS  not-accessible
  STATUS      current
  DESCRIPTION "Table of QoS MapGroups definitions"
  ::= { alaQoSMIBObjects 23 }

alaQoSMapGroupsEntry OBJECT-TYPE
  SYNTAX      QoSMapGroupsEntry
  MAX-ACCESS  not-accessible
  STATUS      current
  DESCRIPTION "Definition of QoS MapGroups"
  INDEX {
          alaQoSMapGroupsName
        }
  ::= { alaQoSMapGroupsTable 1 }

QoSMapGroupsEntry ::=
  SEQUENCE
  {
    alaQoSMapGroupsName                                     SnmpAdminString,
    alaQoSMapGroupsSource                                   INTEGER,
    alaQoSMapGroupsStatus                                   RowStatus
  }

alaQoSMapGroupsName OBJECT-TYPE
  SYNTAX      SnmpAdminString (SIZE(0..31))
  MAX-ACCESS  not-accessible
  STATUS      current
  DESCRIPTION "Name of map group"
  ::= { alaQoSMapGroupsEntry 1 }

alaQoSMapGroupsSource OBJECT-TYPE
  SYNTAX      INTEGER {
                ldap (1),
                cli (2),
                blt (3),
                api (4),
                imp (5)
              }
  MAX-ACCESS  read-create
  STATUS      current
  DESCRIPTION "What entity created the map group."
  DEFVAL      { cli }
  ::= { alaQoSMapGroupsEntry 2 }

alaQoSMapGroupsStatus OBJECT-TYPE
  SYNTAX      RowStatus
  MAX-ACCESS  read-create
  STATUS      current
  DESCRIPTION "Used to create/delete map groups according to the
               RowStatus convention"
  ::= { alaQoSMapGroupsEntry 3 }


--
-- Definition of map group table
--

alaQoSAppliedMapGroupsTable OBJECT-TYPE
  SYNTAX      SEQUENCE OF QoSAppliedMapGroupsEntry
  MAX-ACCESS  not-accessible
  STATUS      current
  DESCRIPTION "Table of QoS AppliedMapGroups definitions"
  ::= { alaQoSMIBObjects 24 }

alaQoSAppliedMapGroupsEntry OBJECT-TYPE
  SYNTAX      QoSAppliedMapGroupsEntry
  MAX-ACCESS  not-accessible
  STATUS      current
  DESCRIPTION "Definition of QoS AppliedMapGroups"
  INDEX {
          alaQoSAppliedMapGroupsName
        }
  ::= { alaQoSAppliedMapGroupsTable 1 }

QoSAppliedMapGroupsEntry ::=
  SEQUENCE
  {
    alaQoSAppliedMapGroupsName                              SnmpAdminString,
    alaQoSAppliedMapGroupsSource                            INTEGER,
    alaQoSAppliedMapGroupsStatus                            RowStatus
  }

alaQoSAppliedMapGroupsName OBJECT-TYPE
  SYNTAX      SnmpAdminString (SIZE(0..31))
  MAX-ACCESS  not-accessible
  STATUS      current
  DESCRIPTION "Name of map group"
  ::= { alaQoSAppliedMapGroupsEntry 1 }

alaQoSAppliedMapGroupsSource OBJECT-TYPE
  SYNTAX      INTEGER {
                ldap (1),
                cli (2),
                blt (3),
                api (4),
                imp (5)
              }
  MAX-ACCESS  read-only
  STATUS      current
  DESCRIPTION "What entity created the map group."
  ::= { alaQoSAppliedMapGroupsEntry 2 }

alaQoSAppliedMapGroupsStatus OBJECT-TYPE
  SYNTAX      RowStatus
  MAX-ACCESS  read-only
  STATUS      current
  DESCRIPTION "Used to create/delete map groups according to the
               RowStatus convention"
  ::= { alaQoSAppliedMapGroupsEntry 3 }


--
-- Definition of map group entry table
--

alaQoSMapGroupTable OBJECT-TYPE
  SYNTAX      SEQUENCE OF QoSMapGroupEntry
  MAX-ACCESS  not-accessible
  STATUS      current
  DESCRIPTION "Table of QoS MapGroup definitions"
  ::= { alaQoSMIBObjects 25 }

alaQoSMapGroupEntry OBJECT-TYPE
  SYNTAX      QoSMapGroupEntry
  MAX-ACCESS  not-accessible
  STATUS      current
  DESCRIPTION "Definition of QoS MapGroup"
  INDEX {
          alaQoSMapGroupsName,
          alaQoSMapGroupKey,
          alaQoSMapGroupKeyEnd,
          alaQoSMapGroupValue
        }
  ::= { alaQoSMapGroupTable 1 }

QoSMapGroupEntry ::=
  SEQUENCE
  {
    alaQoSMapGroupKey                                       Integer32,
    alaQoSMapGroupKeyEnd                                    Integer32,
    alaQoSMapGroupValue                                     Integer32,
    alaQoSMapGroupStatus                                    RowStatus
  }

alaQoSMapGroupKey OBJECT-TYPE
  SYNTAX      Integer32 (0..63)
  MAX-ACCESS  not-accessible
  STATUS      current
  DESCRIPTION "Key range start of map group entry."
  ::= { alaQoSMapGroupEntry 1 }

alaQoSMapGroupKeyEnd OBJECT-TYPE
  SYNTAX      Integer32 (0..63)
  MAX-ACCESS  not-accessible
  STATUS      current
  DESCRIPTION "Key range end for map group entries.  Key range end
               must be greater than key range start to indicate a range.
               When '0', use key range start as a single key."
  ::= { alaQoSMapGroupEntry 2 }

alaQoSMapGroupValue OBJECT-TYPE
  SYNTAX      Integer32 (0..63)
  MAX-ACCESS  not-accessible
  STATUS      current
  DESCRIPTION "Value for map group entries.  Value to stamp on traffic when
               keys in the proper range are seen."
  ::= { alaQoSMapGroupEntry 3 }

alaQoSMapGroupStatus OBJECT-TYPE
  SYNTAX      RowStatus
  MAX-ACCESS  read-create
  STATUS      current
  DESCRIPTION "Used to create/delete map group entries according to the
               RowStatus convention"
  ::= { alaQoSMapGroupEntry 4 }


--
-- Definition of map group entry table
--

alaQoSAppliedMapGroupTable OBJECT-TYPE
  SYNTAX      SEQUENCE OF QoSAppliedMapGroupEntry
  MAX-ACCESS  not-accessible
  STATUS      current
  DESCRIPTION "Table of QoS AppliedMapGroup definitions"
  ::= { alaQoSMIBObjects 26 }

alaQoSAppliedMapGroupEntry OBJECT-TYPE
  SYNTAX      QoSAppliedMapGroupEntry
  MAX-ACCESS  not-accessible
  STATUS      current
  DESCRIPTION "Definition of QoS AppliedMapGroup"
  INDEX {
          alaQoSAppliedMapGroupsName,
          alaQoSAppliedMapGroupKey,
          alaQoSAppliedMapGroupKeyEnd,
          alaQoSAppliedMapGroupValue
        }
  ::= { alaQoSAppliedMapGroupTable 1 }

QoSAppliedMapGroupEntry ::=
  SEQUENCE
  {
    alaQoSAppliedMapGroupKey                                Integer32,
    alaQoSAppliedMapGroupKeyEnd                             Integer32,
    alaQoSAppliedMapGroupValue                              Integer32,
    alaQoSAppliedMapGroupStatus                             RowStatus
  }

alaQoSAppliedMapGroupKey OBJECT-TYPE
  SYNTAX      Integer32 (0..63)
  MAX-ACCESS  not-accessible
  STATUS      current
  DESCRIPTION "Key range start of map group entry."
  ::= { alaQoSAppliedMapGroupEntry 1 }

alaQoSAppliedMapGroupKeyEnd OBJECT-TYPE
  SYNTAX      Integer32 (0..63)
  MAX-ACCESS  not-accessible
  STATUS      current
  DESCRIPTION "Key range end for map group entries.  Key range end
               must be greater than key range start to indicate a range.
               When '0', use key range start as a single key."
  ::= { alaQoSAppliedMapGroupEntry 2 }

alaQoSAppliedMapGroupValue OBJECT-TYPE
  SYNTAX      Integer32 (0..63)
  MAX-ACCESS  not-accessible
  STATUS      current
  DESCRIPTION "Value for map group entries.  Value to stamp on traffic when
               keys in the proper range are seen."
  ::= { alaQoSAppliedMapGroupEntry 3 }

alaQoSAppliedMapGroupStatus OBJECT-TYPE
  SYNTAX      RowStatus
  MAX-ACCESS  read-only
  STATUS      current
  DESCRIPTION "Used to create/delete map group entries according to the
               RowStatus convention"
  ::= { alaQoSAppliedMapGroupEntry 4 }


--
-- Definition of action table
--

alaQoSActionTable OBJECT-TYPE
  SYNTAX      SEQUENCE OF QoSActionEntry
  MAX-ACCESS  not-accessible
  STATUS      current
  DESCRIPTION "Table of QoS Action definitions"
  ::= { alaQoSMIBObjects 27 }

alaQoSActionEntry OBJECT-TYPE
  SYNTAX      QoSActionEntry
  MAX-ACCESS  not-accessible
  STATUS      current
  DESCRIPTION "Definition of QoS Action"
  INDEX {
          alaQoSActionName
        }
  ::= { alaQoSActionTable 1 }

QoSActionEntry ::=
  SEQUENCE
  {
    alaQoSActionName                                        SnmpAdminString,
    alaQoSActionSource                                      INTEGER,
    alaQoSActionDisposition                                 INTEGER,
    alaQoSActionMaximumBandwidth                            Integer32,
    alaQoSActionMaximumBandwidthStatus                      INTEGER,
    alaQoSActionPriority                                    Integer32,
    alaQoSActionPriorityStatus                              INTEGER,
    alaQoSActionShared                                      INTEGER,
    alaQoSActionMaximumDepth                                Integer32,
    alaQoSActionMaximumDepthStatus                          INTEGER,
    alaQoSAction8021p                                       Integer32,
    alaQoSAction8021pStatus                                 INTEGER,
    alaQoSActionTos                                         Integer32,
    alaQoSActionTosStatus                                   INTEGER,
    alaQoSActionDscp                                        Integer32,
    alaQoSActionDscpStatus                                  INTEGER,
    alaQoSActionMapFrom                                     INTEGER,
    alaQoSActionMapTo                                       INTEGER,
    alaQoSActionMapGroup                                    SnmpAdminString,
    alaQoSActionMapGroupStatus                              INTEGER,
    alaQoSActionLoadBalanceGroup                            SnmpAdminString,
    alaQoSActionLoadBalanceGroupStatus                      INTEGER,
    alaQoSActionPermanentGatewayIpAddr                      IpAddress,
    alaQoSActionPermanentGatewayIpAddrStatus                INTEGER,
    alaQoSActionAlternateGatewayIpAddr                      IpAddress,
    alaQoSActionAlternateGatewayIpAddrStatus                INTEGER,
    alaQoSActionRowStatus                                   RowStatus,
    alaQoSActionNocache                                     INTEGER,
    alaQoSActionPortdisable                                 INTEGER,
    alaQoSActionRedirectSlot                                Integer32,
    alaQoSActionRedirectSlotStatus                          INTEGER,
    alaQoSActionRedirectPort                                Integer32,
    alaQoSActionRedirectAgg                                 Integer32,
    alaQoSActionRedirectAggStatus                           INTEGER,
    alaQoSActionMirrorSlot                                  Integer32,
    alaQoSActionMirrorPort                                  Integer32,
    alaQoSActionMirrorMode                                  INTEGER,
    alaQoSActionMirrorModeStatus                            INTEGER,
    alaQoSActionCIR                                         Integer32,
    alaQoSActionCIRStatus                                   INTEGER,
    alaQoSActionCBS                                         Integer32,
    alaQoSActionCBSStatus                                   INTEGER,
    alaQoSActionPIR                                         Integer32,
    alaQoSActionPIRStatus                                   INTEGER,
    alaQoSActionPBS                                         Integer32,
    alaQoSActionPBSStatus                                   INTEGER,
    alaQoSActionCPUPriority                                 Integer32,
    alaQoSActionCPUPriorityStatus                           INTEGER,
    alaQoSActionColorOnly		                    INTEGER
  }

alaQoSActionName OBJECT-TYPE
  SYNTAX      SnmpAdminString (SIZE(0..31))
  MAX-ACCESS  not-accessible
  STATUS      current
  DESCRIPTION "Name of action"
  ::= { alaQoSActionEntry 1 }

alaQoSActionSource OBJECT-TYPE
  SYNTAX      INTEGER {
                ldap (1),
                cli (2),
                blt (3),
                api (4),
                imp (5)
              }
  MAX-ACCESS  read-create
  STATUS      current
  DESCRIPTION "What entity created the action."
  DEFVAL      { cli }
  ::= { alaQoSActionEntry 2 }

alaQoSActionDisposition OBJECT-TYPE
  SYNTAX      INTEGER {
                accept (1),
                drop (2),
                deny (3)
              }
  MAX-ACCESS  read-create
  STATUS      current
  DESCRIPTION "Disposition of traffic using the action.
               Use to filter out unwanted traffic."
  DEFVAL      { accept }
  ::= { alaQoSActionEntry 3 }

alaQoSActionMaximumBandwidth OBJECT-TYPE
  SYNTAX      Integer32
  MAX-ACCESS  read-create
  STATUS      current
  DESCRIPTION "Maximum bandwidth (Kbits/sec) allowed for traffic"
  DEFVAL      { 0 }
  ::= { alaQoSActionEntry 4 }

alaQoSActionMaximumBandwidthStatus OBJECT-TYPE
  SYNTAX      INTEGER {
                enabled (1),
                disabled (2)
              }
  MAX-ACCESS  read-create
  STATUS      current
  DESCRIPTION "Status field indicating whether maximum bandwidth
               is specified(enabled) or not(disabled)."
  DEFVAL      { disabled }
  ::= { alaQoSActionEntry 5 }

alaQoSActionPriority OBJECT-TYPE
  SYNTAX      Integer32 (0..7)
  MAX-ACCESS  read-create
  STATUS      current
  DESCRIPTION "Internal and queueing priority to use for traffic."
  DEFVAL      { 0 }
  ::= { alaQoSActionEntry 6 }

alaQoSActionPriorityStatus OBJECT-TYPE
  SYNTAX      INTEGER {
                enabled (1),
                disabled (2)
              }
  MAX-ACCESS  read-create
  STATUS      current
  DESCRIPTION "Status field indicating whether priority
               is specified(enabled) or not(disabled)."
  DEFVAL      { disabled }
  ::= { alaQoSActionEntry 7 }

alaQoSActionShared OBJECT-TYPE
  SYNTAX      INTEGER {
                yes (1),
                no (2)
              }
  MAX-ACCESS  read-create
  STATUS      current
  DESCRIPTION "When enabled, try and share any resources
               (queues/limiters/descriptors) when more than one policy uses
               the same action."
  DEFVAL      { no }
  ::= { alaQoSActionEntry 8 }

alaQoSActionMaximumDepth OBJECT-TYPE
  SYNTAX      Integer32
  MAX-ACCESS  read-create
  STATUS      current
  DESCRIPTION "Maximum depth (Kbytes) of queues for traffic.
               Used for EBS in tri-color marker applications."
  DEFVAL      { 0 }
  ::= { alaQoSActionEntry 9 }

alaQoSActionMaximumDepthStatus OBJECT-TYPE
  SYNTAX      INTEGER {
                enabled (1),
                disabled (2)
              }
  MAX-ACCESS  read-create
  STATUS      current
  DESCRIPTION "Status field indicating whether maximum depth
               is specified(enabled) or not(disabled)."
  DEFVAL      { disabled }
  ::= { alaQoSActionEntry 10 }

alaQoSAction8021p OBJECT-TYPE
  SYNTAX      Integer32 (0..7)
  MAX-ACCESS  read-create
  STATUS      current
  DESCRIPTION "802.1p value to stamp on traffic."
  DEFVAL      { 0 }
  ::= { alaQoSActionEntry 11 }

alaQoSAction8021pStatus OBJECT-TYPE
  SYNTAX      INTEGER {
                enabled (1),
                disabled (2)
              }
  MAX-ACCESS  read-create
  STATUS      current
  DESCRIPTION "Status field indicating whether 802.1p
               is specified(enabled) or not(disabled)."
  DEFVAL      { disabled }
  ::= { alaQoSActionEntry 12 }

alaQoSActionTos OBJECT-TYPE
  SYNTAX      Integer32 (0..7)
  MAX-ACCESS  read-create
  STATUS      current
  DESCRIPTION "TOS value to stamp on traffic. (High 3 bits of TOS byte)"
  DEFVAL      { 0 }
  ::= { alaQoSActionEntry 13 }

alaQoSActionTosStatus OBJECT-TYPE
  SYNTAX      INTEGER {
                enabled (1),
                disabled (2)
              }
  MAX-ACCESS  read-create
  STATUS      current
  DESCRIPTION "Status field indicating whether TOS
               is specified(enabled) or not(disabled)."
  DEFVAL      { disabled }
  ::= { alaQoSActionEntry 14 }

alaQoSActionDscp OBJECT-TYPE
  SYNTAX      Integer32 (0..63)
  MAX-ACCESS  read-create
  STATUS      current
  DESCRIPTION "TOS value to stamp on traffic. (High 6 bits of TOS byte)"
  DEFVAL      { 0 }
  ::= { alaQoSActionEntry 15 }

alaQoSActionDscpStatus OBJECT-TYPE
  SYNTAX      INTEGER {
                enabled (1),
                disabled (2)
              }
  MAX-ACCESS  read-create
  STATUS      current
  DESCRIPTION "Status field indicating whether DSCP
               is specified(enabled) or not(disabled)."
  DEFVAL      { disabled }
  ::= { alaQoSActionEntry 16 }

alaQoSActionMapFrom OBJECT-TYPE
  SYNTAX      INTEGER {
                b8021p (1),
                tos (2),
                dscp (3)
              }
  MAX-ACCESS  read-create
  STATUS      current
  DESCRIPTION "What field to use as key for mapping 802.1p/TOS/DSCP priorities"
  DEFVAL      { b8021p }
  ::= { alaQoSActionEntry 17 }

alaQoSActionMapTo OBJECT-TYPE
  SYNTAX      INTEGER {
                b8021p (1),
                tos (2),
                dscp (3)
              }
  MAX-ACCESS  read-create
  STATUS      current
  DESCRIPTION "What field to rewrite due to remapping 802.1p/TOS/DSCP
               priorities"
  DEFVAL      { b8021p }
  ::= { alaQoSActionEntry 18 }

alaQoSActionMapGroup OBJECT-TYPE
  SYNTAX      SnmpAdminString (SIZE(0..31))
  MAX-ACCESS  read-create
  STATUS      current
  DESCRIPTION "Name of the map group to use when remapping 802.1p/TOS/DSCP
               priorities."
  ::= { alaQoSActionEntry 19 }

alaQoSActionMapGroupStatus OBJECT-TYPE
  SYNTAX      INTEGER {
                enabled (1),
                disabled (2)
              }
  MAX-ACCESS  read-create
  STATUS      current
  DESCRIPTION "Status field indicating whether a map group
               is specified(enabled) or not(disabled)."
  DEFVAL      { disabled }
  ::= { alaQoSActionEntry 20 }

alaQoSActionLoadBalanceGroup OBJECT-TYPE
  SYNTAX      SnmpAdminString (SIZE(0..23))
  MAX-ACCESS  read-create
  STATUS      current
  DESCRIPTION "Name of load balance group to use for traffic"
  ::= { alaQoSActionEntry 21 }

alaQoSActionLoadBalanceGroupStatus OBJECT-TYPE
  SYNTAX      INTEGER {
                enabled (1),
                disabled (2)
              }
  MAX-ACCESS  read-create
  STATUS      current
  DESCRIPTION "Status field indicating whether load balanace group
               is specified(enabled) or not(disabled)."
  DEFVAL      { disabled }
  ::= { alaQoSActionEntry 22 }

alaQoSActionPermanentGatewayIpAddr OBJECT-TYPE
  SYNTAX      IpAddress
  MAX-ACCESS  read-create
  STATUS      current
  DESCRIPTION "Next hop gateway to use for traffic"
  DEFVAL      { '00000000'h }
  ::= { alaQoSActionEntry 23 }

alaQoSActionPermanentGatewayIpAddrStatus OBJECT-TYPE
  SYNTAX      INTEGER {
                enabled (1),
                disabled (2)
              }
  MAX-ACCESS  read-create
  STATUS      current
  DESCRIPTION "Status field indicating whether permanent gateway IP address
               is specified(enabled) or not(disabled)."
  DEFVAL      { disabled }
  ::= { alaQoSActionEntry 24 }

alaQoSActionAlternateGatewayIpAddr OBJECT-TYPE
  SYNTAX      IpAddress
  MAX-ACCESS  read-create
  STATUS      current
  DESCRIPTION "Next hop gateway to use for traffic that doesn't have an
               explicit route.  Use this gateway instead of default routes."
  DEFVAL      { '00000000'h }
  ::= { alaQoSActionEntry 25 }

alaQoSActionAlternateGatewayIpAddrStatus OBJECT-TYPE
  SYNTAX      INTEGER {
                enabled (1),
                disabled (2)
              }
  MAX-ACCESS  read-create
  STATUS      current
  DESCRIPTION "Status field indicating whether alternate gateway IP address
               is specified(enabled) or not(disabled)."
  DEFVAL      { disabled }
  ::= { alaQoSActionEntry 26 }

alaQoSActionRowStatus OBJECT-TYPE
  SYNTAX      RowStatus
  MAX-ACCESS  read-create
  STATUS      current
  DESCRIPTION "Used to create/delete actions according to the
               RowStatus convention"
  ::= { alaQoSActionEntry 27 }

alaQoSActionNocache OBJECT-TYPE
  SYNTAX      INTEGER {
                yes (1),
                no (2)
              }
  MAX-ACCESS  read-create
  STATUS      current
  DESCRIPTION "When enabled, don't make hardware entries for matching flows."
  DEFVAL      { no }
  ::= { alaQoSActionEntry 28 }

alaQoSActionPortdisable OBJECT-TYPE
  SYNTAX      INTEGER {
                yes (1),
                no (2)
              }
  MAX-ACCESS  read-create
  STATUS      current
  DESCRIPTION "When enabled, disable the physical source port of the traffic."
  DEFVAL      { no }
  ::= { alaQoSActionEntry 29 }

alaQoSActionRedirectSlot OBJECT-TYPE
  SYNTAX      Integer32 (0..16)
  MAX-ACCESS  read-create
  STATUS      current
  DESCRIPTION "Destination physical slot for redirected traffic"
  DEFVAL      { 1 }
  ::= { alaQoSActionEntry 30 }

alaQoSActionRedirectSlotStatus OBJECT-TYPE
  SYNTAX      INTEGER {
                enabled (1),
                disabled (2)
              }
  MAX-ACCESS  read-create
  STATUS      current
  DESCRIPTION "Status for alaQoSActionRedirectSlotStatus field"
  DEFVAL      { disabled }
  ::= { alaQoSActionEntry 31 }

alaQoSActionRedirectPort OBJECT-TYPE
  SYNTAX      Integer32 (1..52)
  MAX-ACCESS  read-create
  STATUS      current
  DESCRIPTION "Destination physical port for redirected traffic"
  DEFVAL      { 1 }
  ::= { alaQoSActionEntry 32 }

alaQoSActionRedirectAgg OBJECT-TYPE
  SYNTAX      Integer32 (0..32)
  MAX-ACCESS  read-create
  STATUS      current
  DESCRIPTION "Destination linkagg for redirected traffic"
  DEFVAL      { 0 }
  ::= { alaQoSActionEntry 33 }

alaQoSActionRedirectAggStatus OBJECT-TYPE
  SYNTAX      INTEGER {
                enabled (1),
                disabled (2)
              }
  MAX-ACCESS  read-create
  STATUS      current
  DESCRIPTION "Status for alaQoSActionRedirectAggStatus field"
  DEFVAL      { disabled }
  ::= { alaQoSActionEntry 34 }

alaQoSActionMirrorSlot OBJECT-TYPE
  SYNTAX      Integer32 (0..16)
  MAX-ACCESS  read-create
  STATUS      current
  DESCRIPTION "Destination physical slot for mirrored traffic"
  DEFVAL      { 1 }
  ::= { alaQoSActionEntry 35 }

alaQoSActionMirrorPort OBJECT-TYPE
  SYNTAX      Integer32 (1..52)
  MAX-ACCESS  read-create
  STATUS      current
  DESCRIPTION "Destination physical port for mirrored traffic"
  DEFVAL      { 1 }
  ::= { alaQoSActionEntry 36 }

alaQoSActionMirrorMode OBJECT-TYPE
  SYNTAX      INTEGER {
                ingress(1),
                egress(2),
                both(3)
              }
  MAX-ACCESS  read-create
  STATUS      current
  DESCRIPTION "Mirroring mode"
  DEFVAL      { ingress }
  ::= { alaQoSActionEntry 37 }

alaQoSActionMirrorModeStatus OBJECT-TYPE
  SYNTAX      INTEGER {
                enabled (1),
                disabled (2)
              }
  MAX-ACCESS  read-create
  STATUS      current
  DESCRIPTION "Status for alaQoSActionMirrorMode field"
  DEFVAL      { disabled }
  ::= { alaQoSActionEntry 38 }

alaQoSActionCIR OBJECT-TYPE
  SYNTAX      Integer32
  UNITS       "kilobits per second"
  MAX-ACCESS  read-create
  STATUS      current
  DESCRIPTION "Committed Information Rate - bandwidth values in kilobits per second."
  DEFVAL      { 0 }
  ::= { alaQoSActionEntry 39 }

alaQoSActionCIRStatus OBJECT-TYPE
  SYNTAX      INTEGER {
                enabled (1),
                disabled (2)
              }
  MAX-ACCESS  read-create
  STATUS      current
  DESCRIPTION "Status field indicating whether CIR value is specified(enabled)
                          or not(disabled)."
   DEFVAL      { disabled }
  ::= { alaQoSActionEntry 40 }

alaQoSActionCBS OBJECT-TYPE
  SYNTAX      Integer32(0 .. 2147450880)
  MAX-ACCESS  read-create
  STATUS      current
  DESCRIPTION "Committed Burst Size - bucket size in byte."
  DEFVAL      { 0 }
  ::= { alaQoSActionEntry 41 }

alaQoSActionCBSStatus OBJECT-TYPE
  SYNTAX      INTEGER {
                enabled (1),
                disabled (2)
                }
  MAX-ACCESS  read-create
  STATUS      current
  DESCRIPTION "Status field indicating whether CBS value is specified(enabled)
              or not(disabled)."
  DEFVAL      { disabled }
  ::= { alaQoSActionEntry 42 }

alaQoSActionPIR OBJECT-TYPE
  SYNTAX      Integer32
  UNITS       "kilobits per second"
  MAX-ACCESS  read-create
  STATUS      current
  DESCRIPTION "Peak Information Rate - bandwidth values in kilobits per second."
  DEFVAL      { 0 }
  ::= { alaQoSActionEntry 43 }

alaQoSActionPIRStatus OBJECT-TYPE
  SYNTAX      INTEGER {
                enabled (1),
                disabled (2)
              }
  MAX-ACCESS  read-create
  STATUS      current
  DESCRIPTION "Status field indicating whether PIR value is specified(enabled)
                          or not(disabled)."
   DEFVAL      { disabled }
  ::= { alaQoSActionEntry 44 }

alaQoSActionPBS OBJECT-TYPE
  SYNTAX      Integer32(0 .. 2147450880)
  MAX-ACCESS  read-create
  STATUS      current
  DESCRIPTION "Peak Burst Size - bucket size in byte."
  DEFVAL      { 0 }
  ::= { alaQoSActionEntry 45 }

alaQoSActionPBSStatus OBJECT-TYPE
  SYNTAX      INTEGER {
                enabled (1),
                disabled (2)
                }
  MAX-ACCESS  read-create
  STATUS      current
  DESCRIPTION "Status field indicating whether PBS value is specified(enabled)
              or not(disabled)."
  DEFVAL      { disabled }
  ::= { alaQoSActionEntry 46 }

  alaQoSActionCPUPriority OBJECT-TYPE
  SYNTAX      Integer32(0 .. 7)
  MAX-ACCESS  read-create
  STATUS      current
  DESCRIPTION "Priority for CPU messages."
  DEFVAL      { 0 }
  ::= { alaQoSActionEntry 47 }

alaQoSActionCPUPriorityStatus OBJECT-TYPE
  SYNTAX      INTEGER {
                enabled (1),
                disabled (2)
                }
  MAX-ACCESS  read-create
  STATUS      current
  DESCRIPTION "Status field indicating whether CPU Priority value is specified(enabled)
              or not(disabled)."
  DEFVAL      { disabled }
  ::= { alaQoSActionEntry 48 }

alaQoSActionColorOnly OBJECT-TYPE
  SYNTAX      INTEGER {
                yes (1),
                no (2)
              }
  MAX-ACCESS  read-create
  STATUS      current
  DESCRIPTION "only color red traffic "
  ::= { alaQoSActionEntry 49 }

--
-- Definition of action table
--

alaQoSAppliedActionTable OBJECT-TYPE
  SYNTAX      SEQUENCE OF QoSAppliedActionEntry
  MAX-ACCESS  not-accessible
  STATUS      current
  DESCRIPTION "Table of QoS AppliedAction definitions"
  ::= { alaQoSMIBObjects 28 }

alaQoSAppliedActionEntry OBJECT-TYPE
  SYNTAX      QoSAppliedActionEntry
  MAX-ACCESS  not-accessible
  STATUS      current
  DESCRIPTION "Definition of QoS AppliedAction"
  INDEX {
          alaQoSAppliedActionName
        }
  ::= { alaQoSAppliedActionTable 1 }

QoSAppliedActionEntry ::=
  SEQUENCE
  {
    alaQoSAppliedActionName                                 SnmpAdminString,
    alaQoSAppliedActionSource                               INTEGER,
    alaQoSAppliedActionDisposition                          INTEGER,
    alaQoSAppliedActionMaximumBandwidth                     Integer32,
    alaQoSAppliedActionMaximumBandwidthStatus               INTEGER,
    alaQoSAppliedActionPriority                             Integer32,
    alaQoSAppliedActionPriorityStatus                       INTEGER,
    alaQoSAppliedActionShared                               INTEGER,
    alaQoSAppliedActionMaximumDepth                         Integer32,
    alaQoSAppliedActionMaximumDepthStatus                   INTEGER,
    alaQoSAppliedAction8021p                                Integer32,
    alaQoSAppliedAction8021pStatus                          INTEGER,
    alaQoSAppliedActionTos                                  Integer32,
    alaQoSAppliedActionTosStatus                            INTEGER,
    alaQoSAppliedActionDscp                                 Integer32,
    alaQoSAppliedActionDscpStatus                           INTEGER,
    alaQoSAppliedActionMapFrom                              INTEGER,
    alaQoSAppliedActionMapTo                                INTEGER,
    alaQoSAppliedActionMapGroup                             SnmpAdminString,
    alaQoSAppliedActionMapGroupStatus                       INTEGER,
    alaQoSAppliedActionLoadBalanceGroup                     SnmpAdminString,
    alaQoSAppliedActionLoadBalanceGroupStatus               INTEGER,
    alaQoSAppliedActionPermanentGatewayIpAddr               IpAddress,
    alaQoSAppliedActionPermanentGatewayIpAddrStatus         INTEGER,
    alaQoSAppliedActionAlternateGatewayIpAddr               IpAddress,
    alaQoSAppliedActionAlternateGatewayIpAddrStatus         INTEGER,
    alaQoSAppliedActionRowStatus                            RowStatus,
    alaQoSAppliedActionNocache                              INTEGER,
    alaQoSAppliedActionPortdisable                          INTEGER,
    alaQoSAppliedActionRedirectSlot                         Integer32,
    alaQoSAppliedActionRedirectSlotStatus                   INTEGER,
    alaQoSAppliedActionRedirectPort                         Integer32,
    alaQoSAppliedActionRedirectAgg                          Integer32,
    alaQoSAppliedActionRedirectAggStatus                    INTEGER,
    alaQoSAppliedActionMirrorSlot                           Integer32,
    alaQoSAppliedActionMirrorPort                           Integer32,
    alaQoSAppliedActionMirrorMode                           INTEGER,
    alaQoSAppliedActionMirrorModeStatus                     INTEGER,
    alaQoSAppliedActionCIR                                  Integer32,
    alaQoSAppliedActionCIRStatus                            INTEGER,
    alaQoSAppliedActionCBS                                  Integer32,
    alaQoSAppliedActionCBSStatus                            INTEGER,
    alaQoSAppliedActionPIR                                  Integer32,
    alaQoSAppliedActionPIRStatus                            INTEGER,
    alaQoSAppliedActionPBS                                  Integer32,
    alaQoSAppliedActionPBSStatus                            INTEGER,
    alaQoSAppliedActionCPUPriority                          Integer32,
    alaQoSAppliedActionCPUPriorityStatus                    INTEGER,
    alaQoSAppliedActionColorOnly                            INTEGER
  }

alaQoSAppliedActionName OBJECT-TYPE
  SYNTAX      SnmpAdminString (SIZE(0..31))
  MAX-ACCESS  not-accessible
  STATUS      current
  DESCRIPTION "Name of action"
  ::= { alaQoSAppliedActionEntry 1 }

alaQoSAppliedActionSource OBJECT-TYPE
  SYNTAX      INTEGER {
                ldap (1),
                cli (2),
                blt (3),
                api (4),
                imp (5)
              }
  MAX-ACCESS  read-only
  STATUS      current
  DESCRIPTION "What entity created the action."
  ::= { alaQoSAppliedActionEntry 2 }

alaQoSAppliedActionDisposition OBJECT-TYPE
  SYNTAX      INTEGER {
                accept (1),
                drop (2),
                deny (3)
              }
  MAX-ACCESS  read-only
  STATUS      current
  DESCRIPTION "Disposition of traffic using the action.
               Use to filter out unwanted traffic."
  ::= { alaQoSAppliedActionEntry 3 }

alaQoSAppliedActionMaximumBandwidth OBJECT-TYPE
  SYNTAX      Integer32
  MAX-ACCESS  read-only
  STATUS      current
  DESCRIPTION "Maximum bandwidth (Kbits/sec) allowed for traffic"
  ::= { alaQoSAppliedActionEntry 4 }

alaQoSAppliedActionMaximumBandwidthStatus OBJECT-TYPE
  SYNTAX      INTEGER {
                enabled (1),
                disabled (2)
              }
  MAX-ACCESS  read-only
  STATUS      current
  DESCRIPTION "Status field indicating whether maximum bandwidth
               is specified(enabled) or not(disabled)."
  ::= { alaQoSAppliedActionEntry 5 }

alaQoSAppliedActionPriority OBJECT-TYPE
  SYNTAX      Integer32 (0..7)
  MAX-ACCESS  read-only
  STATUS      current
  DESCRIPTION "Internal and queueing priority to use for traffic."
  ::= { alaQoSAppliedActionEntry 6 }

alaQoSAppliedActionPriorityStatus OBJECT-TYPE
  SYNTAX      INTEGER {
                enabled (1),
                disabled (2)
              }
  MAX-ACCESS  read-only
  STATUS      current
  DESCRIPTION "Status field indicating whether priority
               is specified(enabled) or not(disabled)."
  ::= { alaQoSAppliedActionEntry 7 }

alaQoSAppliedActionShared OBJECT-TYPE
  SYNTAX      INTEGER {
                yes (1),
                no (2)
              }
  MAX-ACCESS  read-only
  STATUS      current
  DESCRIPTION "When enabled, try and share any resources
               (queues/limiters/descriptors) when more than one policy uses
               the same action."
  ::= { alaQoSAppliedActionEntry 8 }

alaQoSAppliedActionMaximumDepth OBJECT-TYPE
  SYNTAX      Integer32
  MAX-ACCESS  read-only
  STATUS      current
  DESCRIPTION "Maximum depth (Kbytes) of queues for traffic.
               Used for EBS in tri-color marker applications."
  ::= { alaQoSAppliedActionEntry 9 }

alaQoSAppliedActionMaximumDepthStatus OBJECT-TYPE
  SYNTAX      INTEGER {
                enabled (1),
                disabled (2)
              }
  MAX-ACCESS  read-only
  STATUS      current
  DESCRIPTION "Status field indicating whether maximum depth
               is specified(enabled) or not(disabled)."
  ::= { alaQoSAppliedActionEntry 10 }

alaQoSAppliedAction8021p OBJECT-TYPE
  SYNTAX      Integer32 (0..7)
  MAX-ACCESS  read-only
  STATUS      current
  DESCRIPTION "802.1p value to stamp on traffic."
  ::= { alaQoSAppliedActionEntry 11 }

alaQoSAppliedAction8021pStatus OBJECT-TYPE
  SYNTAX      INTEGER {
                enabled (1),
                disabled (2)
              }
  MAX-ACCESS  read-only
  STATUS      current
  DESCRIPTION "Status field indicating whether 802.1p
               is specified(enabled) or not(disabled)."
  ::= { alaQoSAppliedActionEntry 12 }

alaQoSAppliedActionTos OBJECT-TYPE
  SYNTAX      Integer32 (0..7)
  MAX-ACCESS  read-only
  STATUS      current
  DESCRIPTION "TOS value to stamp on traffic. (High 3 bits of TOS byte)"
  ::= { alaQoSAppliedActionEntry 13 }

alaQoSAppliedActionTosStatus OBJECT-TYPE
  SYNTAX      INTEGER {
                enabled (1),
                disabled (2)
              }
  MAX-ACCESS  read-only
  STATUS      current
  DESCRIPTION "Status field indicating whether TOS
               is specified(enabled) or not(disabled)."
  ::= { alaQoSAppliedActionEntry 14 }

alaQoSAppliedActionDscp OBJECT-TYPE
  SYNTAX      Integer32 (0..63)
  MAX-ACCESS  read-only
  STATUS      current
  DESCRIPTION "TOS value to stamp on traffic. (High 6 bits of TOS byte)"
  ::= { alaQoSAppliedActionEntry 15 }

alaQoSAppliedActionDscpStatus OBJECT-TYPE
  SYNTAX      INTEGER {
                enabled (1),
                disabled (2)
              }
  MAX-ACCESS  read-only
  STATUS      current
  DESCRIPTION "Status field indicating whether DSCP
               is specified(enabled) or not(disabled)."
  ::= { alaQoSAppliedActionEntry 16 }

alaQoSAppliedActionMapFrom OBJECT-TYPE
  SYNTAX      INTEGER {
                b8021p (1),
                tos (2),
                dscp (3)
              }
  MAX-ACCESS  read-only
  STATUS      current
  DESCRIPTION "What field to use as key for mapping 802.1p/TOS/DSCP priorities"
  ::= { alaQoSAppliedActionEntry 17 }

alaQoSAppliedActionMapTo OBJECT-TYPE
  SYNTAX      INTEGER {
                b8021p (1),
                tos (2),
                dscp (3)
              }
  MAX-ACCESS  read-only
  STATUS      current
  DESCRIPTION "What field to rewrite due to remapping 802.1p/TOS/DSCP
               priorities"
  ::= { alaQoSAppliedActionEntry 18 }

alaQoSAppliedActionMapGroup OBJECT-TYPE
  SYNTAX      SnmpAdminString (SIZE(0..31))
  MAX-ACCESS  read-only
  STATUS      current
  DESCRIPTION "Name of the map group to use when remapping 802.1p/TOS/DSCP
               priorities."
  ::= { alaQoSAppliedActionEntry 19 }

alaQoSAppliedActionMapGroupStatus OBJECT-TYPE
  SYNTAX      INTEGER {
                enabled (1),
                disabled (2)
              }
  MAX-ACCESS  read-only
  STATUS      current
  DESCRIPTION "Status field indicating whether a map group
               is specified(enabled) or not(disabled)."
  ::= { alaQoSAppliedActionEntry 20 }

alaQoSAppliedActionLoadBalanceGroup OBJECT-TYPE
  SYNTAX      SnmpAdminString (SIZE(0..23))
  MAX-ACCESS  read-only
  STATUS      current
  DESCRIPTION "Name of load balance group to use for traffic"
  ::= { alaQoSAppliedActionEntry 21 }

alaQoSAppliedActionLoadBalanceGroupStatus OBJECT-TYPE
  SYNTAX      INTEGER {
                enabled (1),
                disabled (2)
              }
  MAX-ACCESS  read-only
  STATUS      current
  DESCRIPTION "Status field indicating whether load balanace group
               is specified(enabled) or not(disabled)."
  ::= { alaQoSAppliedActionEntry 22 }

alaQoSAppliedActionPermanentGatewayIpAddr OBJECT-TYPE
  SYNTAX      IpAddress
  MAX-ACCESS  read-only
  STATUS      current
  DESCRIPTION "Next hop gateway to use for traffic"
  ::= { alaQoSAppliedActionEntry 23 }

alaQoSAppliedActionPermanentGatewayIpAddrStatus OBJECT-TYPE
  SYNTAX      INTEGER {
                enabled (1),
                disabled (2)
              }
  MAX-ACCESS  read-only
  STATUS      current
  DESCRIPTION "Status field indicating whether permanent gateway IP address
               is specified(enabled) or not(disabled)."
  ::= { alaQoSAppliedActionEntry 24 }

alaQoSAppliedActionAlternateGatewayIpAddr OBJECT-TYPE
  SYNTAX      IpAddress
  MAX-ACCESS  read-only
  STATUS      current
  DESCRIPTION "Next hop gateway to use for traffic that doesn't have an
               explicit route.  Use this gateway instead of default routes."
  ::= { alaQoSAppliedActionEntry 25 }

alaQoSAppliedActionAlternateGatewayIpAddrStatus OBJECT-TYPE
  SYNTAX      INTEGER {
                enabled (1),
                disabled (2)
              }
  MAX-ACCESS  read-only
  STATUS      current
  DESCRIPTION "Status field indicating whether alternate gateway IP address
               is specified(enabled) or not(disabled)."
  ::= { alaQoSAppliedActionEntry 26 }

alaQoSAppliedActionRowStatus OBJECT-TYPE
  SYNTAX      RowStatus
  MAX-ACCESS  read-only
  STATUS      current
  DESCRIPTION "Used to create/delete actions according to the
               RowStatus convention"
  ::= { alaQoSAppliedActionEntry 27 }

alaQoSAppliedActionNocache OBJECT-TYPE
  SYNTAX      INTEGER {
                yes (1),
                no (2)
              }
  MAX-ACCESS  read-only
  STATUS      current
  DESCRIPTION "When enabled, don't make hardware entries for matching flows."
  ::= { alaQoSAppliedActionEntry 28 }

alaQoSAppliedActionPortdisable OBJECT-TYPE
  SYNTAX      INTEGER {
                yes (1),
                no (2)
              }
  MAX-ACCESS  read-only
  STATUS      current
  DESCRIPTION "When enabled, disable the physical source port of the traffic."
  ::= { alaQoSAppliedActionEntry 29 }

alaQoSAppliedActionRedirectSlot OBJECT-TYPE
  SYNTAX      Integer32 (0..16)
  MAX-ACCESS  read-only
  STATUS      current
  DESCRIPTION "Destination physical slot for redirected traffic"
  ::= { alaQoSAppliedActionEntry 30 }

alaQoSAppliedActionRedirectSlotStatus OBJECT-TYPE
  SYNTAX      INTEGER {
                enabled (1),
                disabled (2)
              }
  MAX-ACCESS  read-only
  STATUS      current
  DESCRIPTION "Status for alaQoSAppliedActionRedirectSlotStatus field"
  ::= { alaQoSAppliedActionEntry 31 }

alaQoSAppliedActionRedirectPort OBJECT-TYPE
  SYNTAX      Integer32 (1..52)
  MAX-ACCESS  read-only
  STATUS      current
  DESCRIPTION "Destination physical port for redirected traffic"
  ::= { alaQoSAppliedActionEntry 32 }

alaQoSAppliedActionRedirectAgg OBJECT-TYPE
  SYNTAX      Integer32 (0..32)
  MAX-ACCESS  read-only
  STATUS      current
  DESCRIPTION "Destination linkagg for redirected traffic"
  ::= { alaQoSAppliedActionEntry 33 }

alaQoSAppliedActionRedirectAggStatus OBJECT-TYPE
  SYNTAX      INTEGER {
                enabled (1),
                disabled (2)
              }
  MAX-ACCESS  read-only
  STATUS      current
  DESCRIPTION "Status for alaQoSAppliedActionRedirectAggStatus field"
  ::= { alaQoSAppliedActionEntry 34 }

alaQoSAppliedActionMirrorSlot OBJECT-TYPE
  SYNTAX      Integer32 (0..16)
  MAX-ACCESS  read-only
  STATUS      current
  DESCRIPTION "Destination physical slot for mirrored traffic"
  ::= { alaQoSAppliedActionEntry 35 }

alaQoSAppliedActionMirrorPort OBJECT-TYPE
  SYNTAX      Integer32 (1..52)
  MAX-ACCESS  read-only
  STATUS      current
  DESCRIPTION "Destination physical port for mirrored traffic"
  ::= { alaQoSAppliedActionEntry 36 }

alaQoSAppliedActionMirrorMode OBJECT-TYPE
  SYNTAX      INTEGER {
                ingress(1),
                egress(2),
                both(3)
              }
  MAX-ACCESS  read-only
  STATUS      current
  DESCRIPTION "Mirroring mode"
  DEFVAL      { ingress }
  ::= { alaQoSAppliedActionEntry 37 }

alaQoSAppliedActionMirrorModeStatus OBJECT-TYPE
  SYNTAX      INTEGER {
                enabled (1),
                disabled (2)
              }
  MAX-ACCESS  read-only
  STATUS      current
  DESCRIPTION "Status for alaQoSAppliedActionMirrorMode field"
  ::= { alaQoSAppliedActionEntry 38 }

  alaQoSAppliedActionCIR OBJECT-TYPE
  SYNTAX      Integer32
  UNITS       "kilobits per second"
  MAX-ACCESS  read-create
  STATUS      current
  DESCRIPTION "Committed Information Rate - bandwidth values in kilobits per second."
  DEFVAL      { 0 }
  ::= { alaQoSAppliedActionEntry 39 }

alaQoSAppliedActionCIRStatus OBJECT-TYPE
  SYNTAX      INTEGER {
                enabled (1),
                disabled (2)
              }
  MAX-ACCESS  read-create
  STATUS      current
  DESCRIPTION "Status field indicating whether CIR value is specified(enabled)
                          or not(disabled)."
   DEFVAL      { disabled }
  ::= { alaQoSAppliedActionEntry 40 }

alaQoSAppliedActionCBS OBJECT-TYPE
  SYNTAX      Integer32(0 .. 2147450880)
  MAX-ACCESS  read-create
  STATUS      current
  DESCRIPTION "Committed Burst Size - bucket size in byte."
  DEFVAL      { 0 }
  ::= { alaQoSAppliedActionEntry 41 }

alaQoSAppliedActionCBSStatus OBJECT-TYPE
  SYNTAX      INTEGER {
                enabled (1),
                disabled (2)
                }
  MAX-ACCESS  read-create
  STATUS      current
  DESCRIPTION "Status field indicating whether CBS value is specified(enabled)
              or not(disabled)."
  DEFVAL      { disabled }
  ::= { alaQoSAppliedActionEntry 42 }

  alaQoSAppliedActionPIR OBJECT-TYPE
  SYNTAX      Integer32
  UNITS       "kilobits per second"
  MAX-ACCESS  read-create
  STATUS      current
  DESCRIPTION "Peak Information Rate - bandwidth values in kilobits per second."
  DEFVAL      { 0 }
  ::= { alaQoSAppliedActionEntry 43 }

alaQoSAppliedActionPIRStatus OBJECT-TYPE
  SYNTAX      INTEGER {
                enabled (1),
                disabled (2)
              }
  MAX-ACCESS  read-create
  STATUS      current
  DESCRIPTION "Status field indicating whether PIR value is specified(enabled)
                          or not(disabled)."
   DEFVAL      { disabled }
  ::= { alaQoSAppliedActionEntry 44 }

alaQoSAppliedActionPBS OBJECT-TYPE
  SYNTAX      Integer32(0 .. 2147450880)
  MAX-ACCESS  read-create
  STATUS      current
  DESCRIPTION "Peak Burst Size - bucket size in byte."
  DEFVAL      { 0 }
  ::= { alaQoSAppliedActionEntry 45 }

alaQoSAppliedActionPBSStatus OBJECT-TYPE
  SYNTAX      INTEGER {
                enabled (1),
                disabled (2)
                }
  MAX-ACCESS  read-create
  STATUS      current
  DESCRIPTION "Status field indicating whether PBS value is specified(enabled)
              or not(disabled)."
  DEFVAL      { disabled }
  ::= { alaQoSAppliedActionEntry 46 }

  alaQoSAppliedActionCPUPriority OBJECT-TYPE
  SYNTAX      Integer32(0 .. 7)
  MAX-ACCESS  read-create
  STATUS      current
  DESCRIPTION "Priority for CPU messages."
  DEFVAL      { 0 }
  ::= { alaQoSAppliedActionEntry 47 }

alaQoSAppliedActionCPUPriorityStatus OBJECT-TYPE
  SYNTAX      INTEGER {
                enabled (1),
                disabled (2)
                }
  MAX-ACCESS  read-create
  STATUS      current
  DESCRIPTION "Status field indicating whether CPU Priority value is specified(enabled)
              or not(disabled)."
  DEFVAL      { disabled }
  ::= { alaQoSAppliedActionEntry 48 }

alaQoSAppliedActionColorOnly OBJECT-TYPE
  SYNTAX      INTEGER {
                yes (1),
                no (2)
              }
  MAX-ACCESS  read-create
  STATUS      current
  DESCRIPTION "only color red traffic "
  ::= { alaQoSAppliedActionEntry 49 }


--
-- Definition of port table
--

alaQoSPortTable OBJECT-TYPE
  SYNTAX      SEQUENCE OF QoSPortEntry
  MAX-ACCESS  not-accessible
  STATUS      current
  DESCRIPTION "Table of QoS Port definitions"
  ::= { alaQoSMIBObjects 29 }

alaQoSPortEntry OBJECT-TYPE
  SYNTAX      QoSPortEntry
  MAX-ACCESS  not-accessible
  STATUS      current
  DESCRIPTION "Definition of QoS Port"
  INDEX {
          alaQoSPortSlot,
          alaQoSPortPort
        }
  ::= { alaQoSPortTable 1 }

QoSPortEntry ::=
  SEQUENCE
  {
    alaQoSPortSlot                                          Integer32,
    alaQoSPortPort                                          Integer32,
    alaQoSPortInterfaceType                                 INTEGER,
    alaQoSPortTrusted                                       INTEGER,
    alaQoSPortDefault8021p                                  Integer32,
    alaQoSPortDefaultDSCP                                   Integer32,
    alaQoSPortMaximumDefaultDepth                           Integer32,
    alaQoSPortMaximumDefaultDepthStatus                     INTEGER,
    alaQoSPortReset                                         INTEGER,
    alaQoSPortPhysicalBandwidth                             Integer32,
    alaQoSPortRowStatus                                     RowStatus,
    alaQoSPortDefaultClassification                         INTEGER,
    alaQoSPortMaximumBandwidth                              Integer32,
    alaQoSPortMaximumBandwidthStatus                        INTEGER,
    alaQoSPortMaximumIngBandwidth                           Integer32,
    alaQoSPortMaximumIngBandwidthStatus                     INTEGER,
    alaQoSPortDEIMarking                                    INTEGER,
    alaQoSPortDEIMapping                                    INTEGER
  }

alaQoSPortSlot OBJECT-TYPE
  SYNTAX      Integer32 (0..16)
  MAX-ACCESS  not-accessible
  STATUS      current
  DESCRIPTION "Physical slot port resides on"
  ::= { alaQoSPortEntry 1 }

alaQoSPortPort OBJECT-TYPE
  SYNTAX      Integer32 (0..52)
  MAX-ACCESS  not-accessible
  STATUS      current
  DESCRIPTION "Physical port number"
  ::= { alaQoSPortEntry 2 }

alaQoSPortInterfaceType OBJECT-TYPE
  SYNTAX      INTEGER {
                ethernet (1),
                wan (2),
                ethernet10 (3),
                ethernet100 (4),
                ethernet1G (5),
                ethernet10G (6),
                aggregate (7)
              }
  MAX-ACCESS  read-only
  STATUS      current
  DESCRIPTION "The type of interface QoS matches for this physical port"
  ::= { alaQoSPortEntry 3 }

alaQoSPortTrusted OBJECT-TYPE
  SYNTAX      INTEGER {
                yes (1),
                no (2)
              }
  MAX-ACCESS  read-create
  STATUS      current
  DESCRIPTION "Status of trusting 802.1p/TOS/DSCP values.
               When trusted, 802.1p/DSCP values in the packet are passed
               through the switch.  When untrusted, 802.1p/DSCP values are set
               to the port defaults."
  DEFVAL      { no }
  ::= { alaQoSPortEntry 4 }

alaQoSPortDefault8021p OBJECT-TYPE
  SYNTAX      Integer32 (0..7)
  MAX-ACCESS  read-create
  STATUS      current
  DESCRIPTION "802.1p priority value to use for untagged frames arriving on
               the port and tagged frames when the port is untrusted."
  DEFVAL      { 0 }
  ::= { alaQoSPortEntry 5 }

alaQoSPortDefaultDSCP OBJECT-TYPE
  SYNTAX      Integer32 (0..63)
  MAX-ACCESS  read-create
  STATUS      current
  DESCRIPTION "DSCP value to stamp in frames arriving on the port when the port
               is untrusted"
  DEFVAL      { 0 }
  ::= { alaQoSPortEntry 6 }

alaQoSPortMaximumDefaultDepth OBJECT-TYPE
  SYNTAX      Integer32
  MAX-ACCESS  read-create
  STATUS      current
  DESCRIPTION "Pending maximum depth of egress queues (Kbytes).
               Maximum depth of queues on this port
               Does not take effect until an 'Apply' command is issued"
  DEFVAL      { 0 }
  ::= { alaQoSPortEntry 7 }

alaQoSPortMaximumDefaultDepthStatus OBJECT-TYPE
  SYNTAX      INTEGER {
                enabled (1),
                disabled (2)
              }
  MAX-ACCESS  read-create
  STATUS      current
  DESCRIPTION "Pending status field indicating whether to enforce
               maximum depth on next 'Apply'"
  DEFVAL      { disabled }
  ::= { alaQoSPortEntry 8 }


alaQoSPortReset OBJECT-TYPE
  SYNTAX      INTEGER {
                yes (1),
                no (2)
              }
  MAX-ACCESS  read-create
  STATUS      current
  DESCRIPTION "Reset all QoS parameters to default values"
  DEFVAL      { no }
  ::= { alaQoSPortEntry 9 }

alaQoSPortPhysicalBandwidth OBJECT-TYPE
  SYNTAX      Integer32
  MAX-ACCESS  read-only
  STATUS      current
  DESCRIPTION "Physical bandwidth of port (Kbit/sec)"
  ::= { alaQoSPortEntry 10 }

alaQoSPortRowStatus OBJECT-TYPE
  SYNTAX      RowStatus
  MAX-ACCESS  read-create
  STATUS      current
  DESCRIPTION "Used to create/delete ports according to the
               RowStatus convention"
  ::= { alaQoSPortEntry 11 }


alaQoSPortDefaultClassification OBJECT-TYPE
  SYNTAX      INTEGER {
                b8021p (1),
                tos (2),
                dscp (3)
              }
  MAX-ACCESS  read-create
  STATUS      current
  DESCRIPTION "Ingress traffic classification parameter for Firenze port
               What field to interpret as priority for WRED"
  DEFVAL      { tos }
  ::= { alaQoSPortEntry 12 }

alaQoSPortMaximumBandwidth OBJECT-TYPE
  SYNTAX      Integer32
  MAX-ACCESS  read-create
  STATUS      current
  DESCRIPTION "Maximum egress bandwidth (Kbits/sec).
               Maximum rate to send traffic out this port"
  DEFVAL      { 0 }
  ::= { alaQoSPortEntry 13 }

alaQoSPortMaximumBandwidthStatus OBJECT-TYPE
  SYNTAX      INTEGER {
                enabled (1),
                disabled (2)
              }
  MAX-ACCESS  read-create
  STATUS      current
  DESCRIPTION "Status field indicating whether to enforce
               maximum bandwidth on port."
  DEFVAL      { disabled }
  ::= { alaQoSPortEntry 14 }


alaQoSPortMaximumIngBandwidth OBJECT-TYPE
  SYNTAX      Integer32
  MAX-ACCESS  read-create
  STATUS      current
  DESCRIPTION "Maximum igress bandwidth (Kbits/sec).
               Maximum rate to recieve traffic in on this port"
  DEFVAL      { 0 }
  ::= { alaQoSPortEntry 15 }

alaQoSPortMaximumIngBandwidthStatus OBJECT-TYPE
  SYNTAX      INTEGER {
                enabled (1),
                disabled (2)
              }
  MAX-ACCESS  read-create
  STATUS      current
  DESCRIPTION "Status field indicating whether to enforce
               maximum bandwidth on port."
  DEFVAL      { disabled }
  ::= { alaQoSPortEntry 16 }

alaQoSPortDEIMarking OBJECT-TYPE
  SYNTAX      INTEGER {
                enabled (1),
                disabled (2)
              }
  MAX-ACCESS  read-create
  STATUS      current
  DESCRIPTION "This object specifies if, in egress traffic, the DEI/CFI bit 
               will be set or not for the traffic which is not conformant to 
               SLA (Yellow color packets).

          enabled(1)  -- the DEI/CFI bit will be set in egress traffic.
          disabled(2) -- the DEI/CFI bit will not be set in egress traffic."
  DEFVAL      { disabled }
  ::= { alaQoSPortEntry 19 }

alaQoSPortDEIMapping OBJECT-TYPE
  SYNTAX      INTEGER {
                enabled (1),
                disabled (2)
              }
  MAX-ACCESS  read-create
  STATUS      current
  DESCRIPTION "This object specifies if, in ingress traffic, the DEI/CFI bit
              will be set or not for the traffic which is not conformant to
              SLA (Yellow color packets).

              enabled(1)  -- the DEI/CFI bit will be set in ingress  traffic.
              disabled(2) -- the DEI/CFI bit will not be set in ingress traffic."
  DEFVAL      { disabled }
  ::= { alaQoSPortEntry 20 }

--
-- Definition of config table
--

alaQoSConfig OBJECT IDENTIFIER ::= { alaQoSMIBObjects 30 }

alaQoSConfigEnabled OBJECT-TYPE
  SYNTAX      INTEGER {
                enable (1),
                disable (2)
              }
  MAX-ACCESS  read-write
  STATUS      current
  DESCRIPTION "Is QoS enabled on the switch"
  ::= { alaQoSConfig 1 }

alaQoSConfigTrustPorts OBJECT-TYPE
  SYNTAX      INTEGER {
                yes (1),
                no (2)
              }
  MAX-ACCESS  read-write
  STATUS      current
  DESCRIPTION "Flag to indicate whether to trust the 802.1p/TOS values on
               incoming traffic by default.  Can be overridden on a port by
               port basis."
  ::= { alaQoSConfig 2 }


alaQoSConfigStatsInterval OBJECT-TYPE
  SYNTAX      Integer32 (10..3600)
  MAX-ACCESS  read-write
  STATUS      current
  DESCRIPTION "Interval in seconds for how often statistics are updated"
  ::= { alaQoSConfig 3 }

alaQoSConfigLogLines OBJECT-TYPE
  SYNTAX      Integer32 (0..10240)
  MAX-ACCESS  read-write
  STATUS      current
  DESCRIPTION "Number of log lines to maintain in the QoS log"
  ::= { alaQoSConfig 4 }

alaQoSConfigLogLevel OBJECT-TYPE
  SYNTAX      Integer32 (2..9)
  MAX-ACCESS  read-write
  STATUS      current
  DESCRIPTION "The level of logging desired.  The higher the level, the more
               verbose the logging"
  ::= { alaQoSConfig 5 }

alaQoSConfigLogConsole OBJECT-TYPE
  SYNTAX      INTEGER {
                yes (1),
                no (2)
              }
  MAX-ACCESS  read-write
  STATUS      current
  DESCRIPTION "Whether QoS log events are logged to the console"
  ::= { alaQoSConfig 6 }

alaQoSConfigForwardLog OBJECT-TYPE
  SYNTAX      INTEGER {
                yes (1),
                no (2)
              }
  MAX-ACCESS  read-write
  STATUS      current
  DESCRIPTION "Whether QoS forwards logging events to PolicyManager"
  ::= { alaQoSConfig 7 }

alaQoSConfigClearLog OBJECT-TYPE
  SYNTAX      INTEGER {
                yes (1),
                no (2)
              }
  MAX-ACCESS  read-write
  STATUS      current
  DESCRIPTION "Clear the QoS log"
  ::= { alaQoSConfig 8 }

alaQoSConfigApply OBJECT-TYPE
  SYNTAX      INTEGER {
                yes (1),
                no (2)
              }
  MAX-ACCESS  read-write
  STATUS      current
  DESCRIPTION "Set to apply all pending QoS configuration/policy changes"
  ::= { alaQoSConfig 9 }

alaQoSConfigRevert OBJECT-TYPE
  SYNTAX      INTEGER {
                yes (1),
                no (2)
              }
  MAX-ACCESS  read-write
  STATUS      current
  DESCRIPTION "Set to revert all pending QoS configuration/policy changes"
  ::= { alaQoSConfig 10 }

alaQoSConfigReset OBJECT-TYPE
  SYNTAX      INTEGER {
                yes (1),
                no (2)
              }
  MAX-ACCESS  read-write
  STATUS      current
  DESCRIPTION "Set to reset global QoS configuration parameters to their
               default values"
  ::= { alaQoSConfig 11 }

alaQoSConfigStatsReset OBJECT-TYPE
  SYNTAX      INTEGER {
                yes (1),
                no (2)
              }
  MAX-ACCESS  read-write
  STATUS      current
  DESCRIPTION "Set to reset global QoS statistics counters"
  ::= { alaQoSConfig 12 }

alaQoSConfigFlush OBJECT-TYPE
  SYNTAX      INTEGER {
                yes (1),
                no (2)
              }
  MAX-ACCESS  read-write
  STATUS      current
  DESCRIPTION "Flush all pending policy objects"
  ::= { alaQoSConfig 13 }

alaQoSConfigDebug OBJECT-TYPE
  SYNTAX      Integer32
  MAX-ACCESS  read-write
  STATUS      current
  DESCRIPTION "Possible debug flags for QoS"
  ::= { alaQoSConfig 14 }


alaQoSConfigUserportFilter OBJECT-TYPE
  SYNTAX      Integer32
  MAX-ACCESS  read-create
  STATUS      current
  DESCRIPTION "Events/protocols to filter on a Userport.  Event bits values are:
                  spoof = 1
                  bpdu = 2
                  bgp = 4
                  ospf = 8
                  rip = 16
                  vrrp = 32
                  dhcp-server = 64
                  pim = 128
                  dvmrp = 256
                  is-is = 512
                  dnsreply = 1024"
  ::= { alaQoSConfig 15 }

alaQoSConfigAppliedUserportFilter OBJECT-TYPE
  SYNTAX      Integer32
  MAX-ACCESS  read-only
  STATUS      current
  DESCRIPTION "Events/protocols to filter on a Userport.  Event bits values are:
                  spoof = 1
                  bpdu = 2
                  bgp = 4
                  ospf = 8
                  rip = 16
                  vrrp = 32
                  dhcp-server = 64
                  pim = 128
                  dvmrp = 256
                  is-is = 512
                  dnsreply = 1024"
  ::= { alaQoSConfig 16 }

alaQoSConfigUserportShutdown OBJECT-TYPE
  SYNTAX      Integer32
  MAX-ACCESS  read-create
  STATUS      current
  DESCRIPTION "Events/protocols that trigger admin down of a Userport.
               Event bits values are:
                  spoof = 1
                  bpdu = 2
                  bgp = 4
                  ospf = 8
                  rip = 16
                  vrrp = 32
                  dhcp-server = 64
                  pim = 128
                  dvmrp = 256
                  is-is = 512
                  dnsreply = 1024"
  ::= { alaQoSConfig 17 }

alaQoSConfigAppliedUserportShutdown OBJECT-TYPE
  SYNTAX      Integer32
  MAX-ACCESS  read-only
  STATUS      current
  DESCRIPTION "Events/protocols that trigger admin down of a Userport.
               Event bits values are:
                  spoof = 1
                  bpdu = 2
                  bgp = 4
                  ospf = 8
                  rip = 16
                  vrrp = 32
                  dhcp-server = 64
                  pim = 128
                  dvmrp = 256
                  is-is = 512
                  dnsreply = 1024"
  ::= { alaQoSConfig 18 }

alaQoSConfigAutoPhones OBJECT-TYPE
  SYNTAX      INTEGER {
                pri0 (0),
                pri1 (1),
                pri2 (2),
                pri3 (3),
                pri4 (4),
                pri5 (5),
                pri6 (6),
                pri7 (7),
                trusted (8),
                disable (9)
              }
  MAX-ACCESS  read-write
  STATUS      current
  DESCRIPTION "Auto configure CSBU Phones
              pri0-7 - will replace the priority.
              trusted - will allow priority from the orginator to be used.
              disable - will unconfigure to feature."
  ::= { alaQoSConfig 19 }

alaQoSConfigQMPage OBJECT-TYPE
  SYNTAX      INTEGER {
                yes (1),
                no (2)
              }
  MAX-ACCESS  read-write
  STATUS      current
  DESCRIPTION "Flag to indicate whether to send back a quarantined page when a client is quarantined but a remediation URL is not specified."
  ::= { alaQoSConfig 20 }

alaQoSConfigQMMACGroup OBJECT-TYPE
  SYNTAX        SnmpAdminString (SIZE(0..31))
  MAX-ACCESS    read-write
  STATUS        current
  DESCRIPTION "Group name for quarantine manager quarantined MACs."
  ::= { alaQoSConfig 21 }

alaQoSConfigQMPath OBJECT-TYPE
  SYNTAX        SnmpAdminString (SIZE(0..255))
  MAX-ACCESS    read-write
  STATUS        current
  DESCRIPTION "Default path for remediation server redirect."
  ::= { alaQoSConfig 22 }
alaQoSConfigDEIMapping OBJECT-TYPE
  SYNTAX      INTEGER {
                enabled (1),
                disabled (2)
              }
  MAX-ACCESS  read-create
  STATUS      current
  DESCRIPTION "This object specifies, in ingress traffic, the DEI/CFI bit is mapped
              or not to internal drop precedence or yellow color.

              enabled(1)  -- the DEI/CFI bit is mapped to internal drop precedence or yellow
                             color if that bit is set.
              disabled(2) -- the DEI/CFI bit is not mapped to drop precedence or yellow
                             color."
  DEFVAL      { disabled }
  ::= { alaQoSConfig 23 }

alaQoSConfigDEIMarking OBJECT-TYPE
  SYNTAX      INTEGER {
                enabled (1),
                disabled (2)
              }
  MAX-ACCESS  read-create
  STATUS      current
  DESCRIPTION "This object specifies, in egress traffic, the DEI/CFI bit is mapped
              or not to internal drop precedence or yellow color.

          enabled(1) --  the DEI/CFI bit is mapped to internal drop precedence or yellow
                         color if that bit is set.
          disabled(2) -- the DEI/CFI bit is not mapped to drop precedence or yellow
                         color."
  DEFVAL      { disabled }
  ::= { alaQoSConfig 24 }

--
-- Definition of statistics table
--

alaQoSStats OBJECT IDENTIFIER ::= { alaQoSMIBObjects 31 }


alaQoSStatsSpoofedEvents OBJECT-TYPE
  SYNTAX      Counter32
  MAX-ACCESS  read-only
  STATUS      current
  DESCRIPTION "Total Number of spoofed events"
  ::= { alaQoSStats 1 }

alaQoSStatsNonSpoofedEvents OBJECT-TYPE
  SYNTAX      Counter32
  MAX-ACCESS  read-only
  STATUS      current
  DESCRIPTION "Total number of non-spoofed events"
  ::= { alaQoSStats 2 }



--
-- Definition of validity period table
--

alaQoSValidityPeriodTable OBJECT-TYPE
  SYNTAX      SEQUENCE OF QoSValidityPeriodEntry
  MAX-ACCESS  not-accessible
  STATUS      current
  DESCRIPTION "Table of QoS ValidityPeriod definitions"
  ::= { alaQoSMIBObjects 32 }

alaQoSValidityPeriodEntry OBJECT-TYPE
  SYNTAX      QoSValidityPeriodEntry
  MAX-ACCESS  not-accessible
  STATUS      current
  DESCRIPTION "Definition of QoS ValidityPeriod"
  INDEX {
          alaQoSValidityPeriodName
        }
  ::= { alaQoSValidityPeriodTable 1 }

QoSValidityPeriodEntry ::=
  SEQUENCE
  {
    alaQoSValidityPeriodName                                SnmpAdminString,
    alaQoSValidityPeriodSource                              INTEGER,
    alaQoSValidityPeriodDays                                Integer32,
    alaQoSValidityPeriodDaysStatus                          INTEGER,
    alaQoSValidityPeriodMonths                              Integer32,
    alaQoSValidityPeriodMonthsStatus                        INTEGER,
    alaQoSValidityPeriodHour                                SnmpAdminString,
    alaQoSValidityPeriodHourStatus                          INTEGER,
    alaQoSValidityPeriodEndHour                             SnmpAdminString,
    alaQoSValidityPeriodInterval                            SnmpAdminString,
    alaQoSValidityPeriodIntervalStatus                      INTEGER,
    alaQoSValidityPeriodEndInterval                         SnmpAdminString,
    alaQoSValidityPeriodRowStatus                           RowStatus
  }

alaQoSValidityPeriodName OBJECT-TYPE
  SYNTAX      SnmpAdminString (SIZE(0..31))
  MAX-ACCESS  not-accessible
  STATUS      current
  DESCRIPTION "Name of validity period"
  ::= { alaQoSValidityPeriodEntry 1 }

alaQoSValidityPeriodSource OBJECT-TYPE
  SYNTAX      INTEGER {
                ldap (1),
                cli (2),
                blt (3),
                api (4),
                imp (5)
              }
  MAX-ACCESS  read-create
  STATUS      current
  DESCRIPTION "What entity created the validity period."
  DEFVAL      { cli }
  ::= { alaQoSValidityPeriodEntry 2 }

alaQoSValidityPeriodDays OBJECT-TYPE
  SYNTAX      Integer32
  MAX-ACCESS  read-create
  STATUS      current
  DESCRIPTION "Bitfield for each day of the week this validity period
               is active.  Monday is least significant, Sunday
               is most significant."
  ::= { alaQoSValidityPeriodEntry 3 }

alaQoSValidityPeriodDaysStatus OBJECT-TYPE
  SYNTAX      INTEGER {
                enabled (1),
                disabled (2)
              }
  MAX-ACCESS  read-create
  STATUS      current
  DESCRIPTION "Status field indicating whether the validity period
               has specific active days of the month."
  DEFVAL      { disabled }
  ::= { alaQoSValidityPeriodEntry 4 }

alaQoSValidityPeriodMonths OBJECT-TYPE
  SYNTAX      Integer32
  MAX-ACCESS  read-create
  STATUS      current
  DESCRIPTION "Bitfield for each month this validity period
               is active.  January is least significant. Decemeber
               is most significant."
  ::= { alaQoSValidityPeriodEntry 5 }

alaQoSValidityPeriodMonthsStatus OBJECT-TYPE
  SYNTAX      INTEGER {
                enabled (1),
                disabled (2)
              }
  MAX-ACCESS  read-create
  STATUS      current
  DESCRIPTION "Status field indicating whether the validity period
               has specific active days of the week."
  DEFVAL      { disabled }
  ::= { alaQoSValidityPeriodEntry 6 }

alaQoSValidityPeriodHour OBJECT-TYPE
  SYNTAX      SnmpAdminString (SIZE(0..7))
  MAX-ACCESS  read-create
  STATUS      current
  DESCRIPTION "Time of day this period becomes active.
               Format is 'hh:mm'"
  ::= { alaQoSValidityPeriodEntry 7 }

alaQoSValidityPeriodHourStatus OBJECT-TYPE
  SYNTAX      INTEGER {
                enabled (1),
                disabled (2)
              }
  MAX-ACCESS  read-create
  STATUS      current
  DESCRIPTION "Status field indicating whether the validity period
               has specific active hours of the day."
  DEFVAL      { disabled }
  ::= { alaQoSValidityPeriodEntry 8 }

alaQoSValidityPeriodEndHour OBJECT-TYPE
  SYNTAX      SnmpAdminString (SIZE(0..7))
  MAX-ACCESS  read-create
  STATUS      current
  DESCRIPTION "Time of day this period becomes inactive.
               Format is 'hh:mm'"
  ::= { alaQoSValidityPeriodEntry 9 }

alaQoSValidityPeriodInterval OBJECT-TYPE
  SYNTAX      SnmpAdminString (SIZE(0..19))
  MAX-ACCESS  read-create
  STATUS      current
  DESCRIPTION "Date/time when the validity period begins.
               Format is 'mm/dd/yyyy hh:mm'"
  ::= { alaQoSValidityPeriodEntry 10 }

alaQoSValidityPeriodIntervalStatus OBJECT-TYPE
  SYNTAX      INTEGER {
                enabled (1),
                disabled (2)
              }
  MAX-ACCESS  read-create
  STATUS      current
  DESCRIPTION "Status field indicating whether the validity period
               has a specific active date-time interval."
  DEFVAL      { disabled }
  ::= { alaQoSValidityPeriodEntry 11 }

alaQoSValidityPeriodEndInterval OBJECT-TYPE
  SYNTAX      SnmpAdminString (SIZE(0..19))
  MAX-ACCESS  read-create
  STATUS      current
  DESCRIPTION "Date/time when the validity period ends.
               Format is 'mm/dd/yyyy hh:mm'"
  ::= { alaQoSValidityPeriodEntry 12 }

alaQoSValidityPeriodRowStatus OBJECT-TYPE
  SYNTAX      RowStatus
  MAX-ACCESS  read-create
  STATUS      current
  DESCRIPTION "Used to create/delete validity periods according
               to the RowStatus convention"
  ::= { alaQoSValidityPeriodEntry 13 }


--
-- Definition of validity period table
--

alaQoSAppliedValidityPeriodTable OBJECT-TYPE
  SYNTAX      SEQUENCE OF QoSAppliedValidityPeriodEntry
  MAX-ACCESS  not-accessible
  STATUS      current
  DESCRIPTION "Table of QoS AppliedValidityPeriod definitions"
  ::= { alaQoSMIBObjects 33 }

alaQoSAppliedValidityPeriodEntry OBJECT-TYPE
  SYNTAX      QoSAppliedValidityPeriodEntry
  MAX-ACCESS  not-accessible
  STATUS      current
  DESCRIPTION "Definition of QoS AppliedValidityPeriod"
  INDEX {
          alaQoSAppliedValidityPeriodName
        }
  ::= { alaQoSAppliedValidityPeriodTable 1 }

QoSAppliedValidityPeriodEntry ::=
  SEQUENCE
  {
    alaQoSAppliedValidityPeriodName                         SnmpAdminString,
    alaQoSAppliedValidityPeriodSource                       INTEGER,
    alaQoSAppliedValidityPeriodDays                         Integer32,
    alaQoSAppliedValidityPeriodDaysStatus                   INTEGER,
    alaQoSAppliedValidityPeriodMonths                       Integer32,
    alaQoSAppliedValidityPeriodMonthsStatus                 INTEGER,
    alaQoSAppliedValidityPeriodHour                         SnmpAdminString,
    alaQoSAppliedValidityPeriodHourStatus                   INTEGER,
    alaQoSAppliedValidityPeriodEndHour                      SnmpAdminString,
    alaQoSAppliedValidityPeriodInterval                     SnmpAdminString,
    alaQoSAppliedValidityPeriodIntervalStatus               INTEGER,
    alaQoSAppliedValidityPeriodEndInterval                  SnmpAdminString,
    alaQoSAppliedValidityPeriodRowStatus                    RowStatus
  }

alaQoSAppliedValidityPeriodName OBJECT-TYPE
  SYNTAX      SnmpAdminString (SIZE(0..31))
  MAX-ACCESS  not-accessible
  STATUS      current
  DESCRIPTION "Name of validity period"
  ::= { alaQoSAppliedValidityPeriodEntry 1 }

alaQoSAppliedValidityPeriodSource OBJECT-TYPE
  SYNTAX      INTEGER {
                ldap (1),
                cli (2),
                blt (3),
                api (4),
                imp (5)
              }
  MAX-ACCESS  read-only
  STATUS      current
  DESCRIPTION "What entity created the validity period."
  ::= { alaQoSAppliedValidityPeriodEntry 2 }

alaQoSAppliedValidityPeriodDays OBJECT-TYPE
  SYNTAX      Integer32
  MAX-ACCESS  read-only
  STATUS      current
  DESCRIPTION "Bitfield for each day of the week this validity period
               is active.  Monday is least significant, Sunday
               is most significant."
  ::= { alaQoSAppliedValidityPeriodEntry 3 }

alaQoSAppliedValidityPeriodDaysStatus OBJECT-TYPE
  SYNTAX      INTEGER {
                enabled (1),
                disabled (2)
              }
  MAX-ACCESS  read-only
  STATUS      current
  DESCRIPTION "Status field indicating whether the validity period
               has specific active days of the month."
  ::= { alaQoSAppliedValidityPeriodEntry 4 }

alaQoSAppliedValidityPeriodMonths OBJECT-TYPE
  SYNTAX      Integer32
  MAX-ACCESS  read-only
  STATUS      current
  DESCRIPTION "Bitfield for each month this validity period
               is active.  January is least significant. Decemeber
               is most significant."
  ::= { alaQoSAppliedValidityPeriodEntry 5 }

alaQoSAppliedValidityPeriodMonthsStatus OBJECT-TYPE
  SYNTAX      INTEGER {
                enabled (1),
                disabled (2)
              }
  MAX-ACCESS  read-only
  STATUS      current
  DESCRIPTION "Status field indicating whether the validity period
               has specific active days of the week."
  ::= { alaQoSAppliedValidityPeriodEntry 6 }

alaQoSAppliedValidityPeriodHour OBJECT-TYPE
  SYNTAX      SnmpAdminString (SIZE(0..7))
  MAX-ACCESS  read-only
  STATUS      current
  DESCRIPTION "Time of day this period becomes active.
               Format is 'hh:mm'"
  ::= { alaQoSAppliedValidityPeriodEntry 7 }

alaQoSAppliedValidityPeriodHourStatus OBJECT-TYPE
  SYNTAX      INTEGER {
                enabled (1),
                disabled (2)
              }
  MAX-ACCESS  read-only
  STATUS      current
  DESCRIPTION "Status field indicating whether the validity period
               has specific active hours of the day."
  ::= { alaQoSAppliedValidityPeriodEntry 8 }

alaQoSAppliedValidityPeriodEndHour OBJECT-TYPE
  SYNTAX      SnmpAdminString (SIZE(0..7))
  MAX-ACCESS  read-only
  STATUS      current
  DESCRIPTION "Time of day this period becomes inactive.
               Format is 'hh:mm'"
  ::= { alaQoSAppliedValidityPeriodEntry 9 }

alaQoSAppliedValidityPeriodInterval OBJECT-TYPE
  SYNTAX      SnmpAdminString (SIZE(0..19))
  MAX-ACCESS  read-only
  STATUS      current
  DESCRIPTION "Date/time when the validity period begins.
               Format is 'mm/dd/yyyy hh:mm'"
  ::= { alaQoSAppliedValidityPeriodEntry 10 }

alaQoSAppliedValidityPeriodIntervalStatus OBJECT-TYPE
  SYNTAX      INTEGER {
                enabled (1),
                disabled (2)
              }
  MAX-ACCESS  read-only
  STATUS      current
  DESCRIPTION "Status field indicating whether the validity period
               has a specific active date-time interval."
  ::= { alaQoSAppliedValidityPeriodEntry 11 }

alaQoSAppliedValidityPeriodEndInterval OBJECT-TYPE
  SYNTAX      SnmpAdminString (SIZE(0..19))
  MAX-ACCESS  read-only
  STATUS      current
  DESCRIPTION "Date/time when the validity period ends.
               Format is 'mm/dd/yyyy hh:mm'"
  ::= { alaQoSAppliedValidityPeriodEntry 12 }

alaQoSAppliedValidityPeriodRowStatus OBJECT-TYPE
  SYNTAX      RowStatus
  MAX-ACCESS  read-only
  STATUS      current
  DESCRIPTION "Used to create/delete validity periods according
               to the RowStatus convention"
  ::= { alaQoSAppliedValidityPeriodEntry 13 }


--
-- Definition of Rule group table
--

alaQoSRuleGroupsTable OBJECT-TYPE
  SYNTAX      SEQUENCE OF QoSRuleGroupsEntry
  MAX-ACCESS  not-accessible
  STATUS      current
  DESCRIPTION "Table of QoS RuleGroups definitions"
  ::= { alaQoSMIBObjects 34 }

alaQoSRuleGroupsEntry OBJECT-TYPE
  SYNTAX      QoSRuleGroupsEntry
  MAX-ACCESS  not-accessible
  STATUS      current
  DESCRIPTION "Definition of QoS RuleGroups"
  INDEX {
          alaQoSRuleGroupsName
        }
  ::= { alaQoSRuleGroupsTable 1 }

QoSRuleGroupsEntry ::=
  SEQUENCE
  {
    alaQoSRuleGroupsName                                 SnmpAdminString,
    alaQoSRuleGroupsSource                               INTEGER,
    alaQoSRuleGroupsType                                 INTEGER,
    alaQoSRuleGroupsEnabled                              INTEGER,
    alaQoSRuleGroupsStatus                               RowStatus
  }

alaQoSRuleGroupsName OBJECT-TYPE
  SYNTAX      SnmpAdminString (SIZE(0..31))
  MAX-ACCESS  not-accessible
  STATUS      current
  DESCRIPTION "Name of rule group"
  ::= { alaQoSRuleGroupsEntry 1 }

alaQoSRuleGroupsSource OBJECT-TYPE
  SYNTAX      INTEGER {
                ldap (1),
                cli (2),
                blt (3),
                api (4),
                imp (5)
              }
  MAX-ACCESS  read-create
  STATUS      current
  DESCRIPTION "What entity created the rule group."
  DEFVAL      { cli }
  ::= { alaQoSRuleGroupsEntry 2 }

alaQoSRuleGroupsType OBJECT-TYPE
  SYNTAX      INTEGER {
                default (1),
                egress (2),
                unp (3)
              }
  MAX-ACCESS  read-create
  STATUS      current
  DESCRIPTION "Type of rule group."
  DEFVAL      { unp }
  ::= { alaQoSRuleGroupsEntry 3 }

alaQoSRuleGroupsEnabled OBJECT-TYPE
  SYNTAX      INTEGER {
                enable (1),
                disable (2)
              }
  MAX-ACCESS  read-create
  STATUS      current
  DESCRIPTION "Is this rule grop enabled or not"
  DEFVAL      { enable }
  ::= { alaQoSRuleGroupsEntry 4 }

alaQoSRuleGroupsStatus OBJECT-TYPE
  SYNTAX      RowStatus
  MAX-ACCESS  read-create
  STATUS      current
  DESCRIPTION "Used to create/delete rule groups according to the
               RowStatus convention"
  ::= { alaQoSRuleGroupsEntry 5 }


--
-- Definition of rule group table
--

alaQoSAppliedRuleGroupsTable OBJECT-TYPE
  SYNTAX      SEQUENCE OF QoSAppliedRuleGroupsEntry
  MAX-ACCESS  not-accessible
  STATUS      current
  DESCRIPTION "Table of QoS AppliedRuleGroups definitions"
  ::= { alaQoSMIBObjects 35 }

alaQoSAppliedRuleGroupsEntry OBJECT-TYPE
  SYNTAX      QoSAppliedRuleGroupsEntry
  MAX-ACCESS  not-accessible
  STATUS      current
  DESCRIPTION "Definition of QoS AppliedRuleGroups"
  INDEX {
          alaQoSAppliedRuleGroupsName
        }
  ::= { alaQoSAppliedRuleGroupsTable 1 }

QoSAppliedRuleGroupsEntry ::=
  SEQUENCE
  {
    alaQoSAppliedRuleGroupsName                          SnmpAdminString,
    alaQoSAppliedRuleGroupsSource                        INTEGER,
    alaQoSAppliedRuleGroupsType                          INTEGER,
    alaQoSAppliedRuleGroupsEnabled                       INTEGER,
    alaQoSAppliedRuleGroupsStatus                        RowStatus
  }

alaQoSAppliedRuleGroupsName OBJECT-TYPE
  SYNTAX      SnmpAdminString (SIZE(0..31))
  MAX-ACCESS  not-accessible
  STATUS      current
  DESCRIPTION "Name of rule group"
  ::= { alaQoSAppliedRuleGroupsEntry 1 }

alaQoSAppliedRuleGroupsSource OBJECT-TYPE
  SYNTAX      INTEGER {
                ldap (1),
                cli (2),
                blt (3),
                api (4),
                imp (5)
              }
  MAX-ACCESS  read-create
  STATUS      current
  DESCRIPTION "What entity created the service group."
  DEFVAL      { cli }
  ::= { alaQoSAppliedRuleGroupsEntry 2 }

alaQoSAppliedRuleGroupsType OBJECT-TYPE
  SYNTAX      INTEGER {
                                                                defualt (1),
                                                                unp (2),
                vrf (3),
                                                                ingress (4),
                                                                egress (5),
                                                                slb (6)
              }
  MAX-ACCESS  read-only
  STATUS      current
  DESCRIPTION "What entity created the rule group."
  ::= { alaQoSAppliedRuleGroupsEntry 3 }

alaQoSAppliedRuleGroupsEnabled OBJECT-TYPE
  SYNTAX      INTEGER {
                enable (1),
                disable (2)
              }
  MAX-ACCESS  read-create
  STATUS      current
  DESCRIPTION "Is this rule grop enabled or not"
  ::= { alaQoSAppliedRuleGroupsEntry 4 }

alaQoSAppliedRuleGroupsStatus OBJECT-TYPE
  SYNTAX      RowStatus
  MAX-ACCESS  read-only
  STATUS      current
  DESCRIPTION "Used to create/delete rule groups according to the
               RowStatus convention"
  ::= { alaQoSAppliedRuleGroupsEntry 5 }

--
-- Definition of rule group entry table
--

alaQoSRuleGroupTable OBJECT-TYPE
  SYNTAX      SEQUENCE OF QoSRuleGroupEntry
  MAX-ACCESS  not-accessible
  STATUS      current
  DESCRIPTION "Table of QoS RuleGroup definitions"
  ::= { alaQoSMIBObjects 36 }

alaQoSRuleGroupEntry OBJECT-TYPE
  SYNTAX      QoSRuleGroupEntry
  MAX-ACCESS  not-accessible
  STATUS      current
  DESCRIPTION "Definition of QoS RuleGroup"
  INDEX {
          alaQoSRuleGroupsName,
          alaQoSRuleGroupRuleName
        }
  ::= { alaQoSRuleGroupTable 1 }

QoSRuleGroupEntry ::=
  SEQUENCE
  {
    alaQoSRuleGroupRuleName                           SnmpAdminString,
    alaQoSRuleGroupMatches                            Counter32,
    alaQoSRuleGroupCountType                          INTEGER,
    alaQoSRuleGroupPacketCount                        Counter64,
    alaQoSRuleGroupByteCount                          Counter64,
    alaQoSRuleGroupStatus                             RowStatus
  }

alaQoSRuleGroupRuleName OBJECT-TYPE
  SYNTAX      SnmpAdminString (SIZE(0..31))
  MAX-ACCESS  not-accessible
  STATUS      current
  DESCRIPTION "Name of rule in rule group entry"
  ::= { alaQoSRuleGroupEntry 1 }

alaQoSRuleGroupMatches OBJECT-TYPE
  SYNTAX      Counter32
  MAX-ACCESS  read-only
  STATUS      current
  DESCRIPTION "Number of times this rule has been matched."
  ::= { alaQoSRuleGroupEntry 2 }

alaQoSRuleGroupCountType OBJECT-TYPE
  SYNTAX      INTEGER {
                packets (1),
                bytes (2)
              }
  MAX-ACCESS  read-create
  STATUS      current
  DESCRIPTION "Which rule statistics counters to update if not all are available"
  DEFVAL      { packets }
  ::= { alaQoSRuleGroupEntry 3 }

alaQoSRuleGroupPacketCount OBJECT-TYPE
  SYNTAX      Counter64
  MAX-ACCESS  read-only
  STATUS      current
  DESCRIPTION "Counter for packets patching this rule"
  ::= { alaQoSRuleGroupEntry 4 }

alaQoSRuleGroupByteCount OBJECT-TYPE
  SYNTAX      Counter64
  MAX-ACCESS  read-only
  STATUS      current
  DESCRIPTION "Counter for bytes matching this rule"
  ::= { alaQoSRuleGroupEntry 5 }

alaQoSRuleGroupStatus OBJECT-TYPE
  SYNTAX      RowStatus
  MAX-ACCESS  read-create
  STATUS      current
  DESCRIPTION "Used to create/delete rule group entries according to the
               RowStatus convention"
  ::= { alaQoSRuleGroupEntry 6 }

--
-- Definition of rule group entry table
--

alaQoSAppliedRuleGroupTable OBJECT-TYPE
  SYNTAX      SEQUENCE OF QoSAppliedRuleGroupEntry
  MAX-ACCESS  not-accessible
  STATUS      current
  DESCRIPTION "Table of QoS AppliedRuleGroup definitions"
  ::= { alaQoSMIBObjects 37 }

alaQoSAppliedRuleGroupEntry OBJECT-TYPE
  SYNTAX      QoSAppliedRuleGroupEntry
  MAX-ACCESS  not-accessible
  STATUS      current
  DESCRIPTION "Definition of QoS AppliedRuleGroup"
  INDEX {
          alaQoSAppliedRuleGroupsName,
          alaQoSAppliedRuleGroupRuleName
        }
  ::= { alaQoSAppliedRuleGroupTable 1 }

QoSAppliedRuleGroupEntry ::=
  SEQUENCE
  {
    alaQoSAppliedRuleGroupRuleName                    SnmpAdminString,
    alaQoSAppliedRuleGroupMatches                     Counter32,
    alaQoSAppliedRuleGroupCountType                   INTEGER,
    alaQoSAppliedRuleGroupPacketCount                 Counter64,
    alaQoSAppliedRuleGroupByteCount                   Counter64,
    alaQoSAppliedRuleGroupStatus                      RowStatus
  }

alaQoSAppliedRuleGroupRuleName OBJECT-TYPE
  SYNTAX      SnmpAdminString (SIZE(0..31))
  MAX-ACCESS  not-accessible
  STATUS      current
  DESCRIPTION "Name of rule in rule group entry"
  ::= { alaQoSAppliedRuleGroupEntry 1 }

alaQoSAppliedRuleGroupMatches OBJECT-TYPE
  SYNTAX      Counter32
  MAX-ACCESS  read-only
  STATUS      current
  DESCRIPTION "Number of times this rule has been matched."
  ::= { alaQoSAppliedRuleGroupEntry 2 }

alaQoSAppliedRuleGroupCountType OBJECT-TYPE
  SYNTAX      INTEGER {
                packets (1),
                bytes (2)
              }
  MAX-ACCESS  read-create
  STATUS      current
  DESCRIPTION "Which rule statistics counters to update if not all are available"
  DEFVAL      { packets }
  ::= { alaQoSAppliedRuleGroupEntry 3 }

alaQoSAppliedRuleGroupPacketCount OBJECT-TYPE
  SYNTAX      Counter64
  MAX-ACCESS  read-only
  STATUS      current
  DESCRIPTION "Counter for packets patching this rule"
  ::= { alaQoSAppliedRuleGroupEntry 4 }

alaQoSAppliedRuleGroupByteCount OBJECT-TYPE
  SYNTAX      Counter64
  MAX-ACCESS  read-only
  STATUS      current
  DESCRIPTION "Counter for bytes matching this rule"
  ::= { alaQoSAppliedRuleGroupEntry 5 }

alaQoSAppliedRuleGroupStatus OBJECT-TYPE
  SYNTAX      RowStatus
  MAX-ACCESS  read-only
  STATUS      current
  DESCRIPTION "Used to create/delete rule group entries according to the
               RowStatus convention"
  ::= { alaQoSAppliedRuleGroupEntry 6 }







alaQoSMIBConformance OBJECT-IDENTITY
  STATUS      current
  DESCRIPTION "Branch for QoS Managed Conformance Information."
  ::= { alaQoSMIB 2 }

alaQoSMIBGroups OBJECT-IDENTITY
  STATUS      current
  DESCRIPTION "Branch for QoS Units of Conformance."
  ::= { alaQoSMIBConformance 1 }

alaQoSMIBCompliances OBJECT-IDENTITY
  STATUS      current
  DESCRIPTION "Branch for QoS Compliance Statements."
  ::= { alaQoSMIBConformance 2 }

alaQoSMIBRuleObjects OBJECT-GROUP
  OBJECTS {
    alaQoSRuleEnabled,
    alaQoSRuleSource,
    alaQoSRulePrecedence,
    alaQoSRuleCondition,
    alaQoSRuleAction,
    alaQoSRuleReflexive,
    alaQoSRuleSave,
    alaQoSRuleLog,
    alaQoSRuleEnforced,
    alaQoSRuleActive,
    alaQoSRuleRowStatus,
    alaQoSRuleValidityPeriod,
    alaQoSRuleValidityPeriodStatus,
    alaQoSRuleLogInterval,
    alaQoSRuleCountType,
    alaQoSRulePacketCount,
    alaQoSRuleByteCount,
    alaQoSRuleType,
    alaQoSRuleTrapEvents,
    alaQoSRuleDefaultList,
    alaQoSRuleGreenPacketCount,
    alaQoSRuleYellowPacketCount,
    alaQoSRuleRedPacketCount,
    alaQoSRuleGreenByteCount,
    alaQoSRuleYellowByteCount,
    alaQoSRuleRedByteCount
  }
  STATUS      current
  DESCRIPTION "Collections of objects providing information for Rules"
  ::= { alaQoSMIBGroups 1 }

alaQoSMIBAppliedRuleObjects OBJECT-GROUP
  OBJECTS {
    alaQoSAppliedRuleEnabled,
    alaQoSAppliedRuleSource,
    alaQoSAppliedRulePrecedence,
    alaQoSAppliedRuleCondition,
    alaQoSAppliedRuleAction,
    alaQoSAppliedRuleReflexive,
    alaQoSAppliedRuleSave,
    alaQoSAppliedRuleLog,
    alaQoSAppliedRuleEnforced,
    alaQoSAppliedRuleActive,
    alaQoSAppliedRuleRowStatus,
    alaQoSAppliedRuleValidityPeriod,
    alaQoSAppliedRuleValidityPeriodStatus,
    alaQoSAppliedRuleLogInterval,
    alaQoSAppliedRuleCountType,
    alaQoSAppliedRulePacketCount,
    alaQoSAppliedRuleByteCount,
    alaQoSAppliedRuleType,
    alaQoSAppliedRuleTrapEvents,
    alaQoSAppliedRuleDefaultList,
    alaQoSAppliedRuleGreenPacketCount,
    alaQoSAppliedRuleYellowPacketCount,
    alaQoSAppliedRuleRedPacketCount,
    alaQoSAppliedRuleGreenByteCount,
    alaQoSAppliedRuleYellowByteCount,
    alaQoSAppliedRuleRedByteCount
  }
  STATUS      current
  DESCRIPTION "Collections of objects providing information
               for applied Rules"
  ::= { alaQoSMIBGroups 2 }

alaQoSMIBConditionObjects OBJECT-GROUP
  OBJECTS {
    alaQoSConditionSource,
    alaQoSConditionSourceSlot,
    alaQoSConditionSourceSlotStatus,
    alaQoSConditionSourcePort,
    alaQoSConditionSourcePortGroup,
    alaQoSConditionSourcePortGroupStatus,
    alaQoSConditionDestinationSlot,
    alaQoSConditionDestinationSlotStatus,
    alaQoSConditionDestinationPort,
    alaQoSConditionDestinationPortGroup,
    alaQoSConditionDestinationPortGroupStatus,
    alaQoSConditionSourceMacAddr,
    alaQoSConditionSourceMacAddrStatus,
    alaQoSConditionSourceMacMask,
    alaQoSConditionSourceMacGroup,
    alaQoSConditionSourceMacGroupStatus,
    alaQoSConditionDestinationMacAddr,
    alaQoSConditionDestinationMacAddrStatus,
    alaQoSConditionDestinationMacMask,
    alaQoSConditionDestinationMacGroup,
    alaQoSConditionDestinationMacGroupStatus,
    alaQoSConditionSourceVlan,
    alaQoSConditionSourceVlanStatus,
    alaQoSConditionDestinationVlan,
    alaQoSConditionDestinationVlanStatus,
    alaQoSCondition8021p,
    alaQoSCondition8021pStatus,
    alaQoSConditionSourceIpAddr,
    alaQoSConditionSourceIpAddrStatus,
    alaQoSConditionSourceIpMask,
    alaQoSConditionSourceNetworkGroup,
    alaQoSConditionSourceNetworkGroupStatus,
    alaQoSConditionDestinationIpAddr,
    alaQoSConditionDestinationIpAddrStatus,
    alaQoSConditionDestinationIpMask,
    alaQoSConditionDestinationNetworkGroup,
    alaQoSConditionDestinationNetworkGroupStatus,
    alaQoSConditionMulticastIpAddr,
    alaQoSConditionMulticastIpAddrStatus,
    alaQoSConditionMulticastIpMask,
    alaQoSConditionMulticastNetworkGroup,
    alaQoSConditionMulticastNetworkGroupStatus,
    alaQoSConditionTos,
    alaQoSConditionTosStatus,
    alaQoSConditionTosMask,
    alaQoSConditionDscp,
    alaQoSConditionDscpStatus,
    alaQoSConditionDscpMask,
    alaQoSConditionIpProtocol,
    alaQoSConditionIpProtocolStatus,
    alaQoSConditionSourceIpPort,
    alaQoSConditionSourceIpPortStatus,
    alaQoSConditionDestinationIpPort,
    alaQoSConditionDestinationIpPortStatus,
    alaQoSConditionService,
    alaQoSConditionServiceStatus,
    alaQoSConditionServiceGroup,
    alaQoSConditionServiceGroupStatus,
    alaQoSConditionIcmpType,
    alaQoSConditionIcmpTypeStatus,
    alaQoSConditionIcmpCode,
    alaQoSConditionIcmpCodeStatus,
    alaQoSConditionRowStatus,
    alaQoSConditionSourcePortEnd,
    alaQoSConditionDestinationPortEnd,
    alaQoSConditionSourceIpPortEnd,
    alaQoSConditionDestinationIpPortEnd,
    alaQoSConditionSourceTcpPort,
    alaQoSConditionSourceTcpPortStatus,
    alaQoSConditionSourceTcpPortEnd,
    alaQoSConditionDestinationTcpPort,
    alaQoSConditionDestinationTcpPortStatus,
    alaQoSConditionDestinationTcpPortEnd,
    alaQoSConditionSourceUdpPort,
    alaQoSConditionSourceUdpPortStatus,
    alaQoSConditionSourceUdpPortEnd,
    alaQoSConditionDestinationUdpPort,
    alaQoSConditionDestinationUdpPortStatus,
    alaQoSConditionDestinationUdpPortEnd,
    alaQoSConditionEthertype,
    alaQoSConditionEthertypeStatus,
    alaQoSConditionTcpFlags,
    alaQoSConditionTcpFlagsStatus,
    alaQoSConditionTcpFlagsVal,
    alaQoSConditionTcpFlagsValStatus,
    alaQoSConditionTcpFlagsMask,
    alaQoSConditionTcpFlagsMaskStatus,
    alaQoSConditionTcpEstablished,
    alaQoSConditionSourceIpv6Addr,
    alaQoSConditionSourceIpv6AddrStatus,
    alaQoSConditionSourceIpv6Mask,
    alaQoSConditionDestinationIpv6Addr,
    alaQoSConditionDestinationIpv6AddrStatus,
    alaQoSConditionDestinationIpv6Mask,
    alaQoSConditionIpv6Traffic,
    alaQoSConditionIpv6NH,
    alaQoSConditionIpv6NHStatus,
    alaQoSConditionIpv6FlowLabel,
    alaQoSConditionIpv6FlowLabelStatus,
    alaQoSConditionMcastIpv6Addr,
    alaQoSConditionMcastIpv6AddrStatus,
    alaQoSConditionMcastIpv6Mask,
    alaQoSConditionDscpEnd,
    alaQoSConditionInnerSourceVlan,
    alaQoSConditionInnerSourceVlanStatus,
    alaQoSConditionInner8021p,
    alaQoSConditionInner8021pStatus,
    alaQoSConditionVrfName,
    alaQoSConditionVrfNameStatus,
    alaQoSConditionFragments
  }

  STATUS      current
  DESCRIPTION "Collections of objects providing information for Conditions"
  ::= { alaQoSMIBGroups 3 }

alaQoSMIBAppliedConditionObjects OBJECT-GROUP
  OBJECTS {
    alaQoSAppliedConditionSource,
    alaQoSAppliedConditionSourceSlot,
    alaQoSAppliedConditionSourceSlotStatus,
    alaQoSAppliedConditionSourcePort,
    alaQoSAppliedConditionSourcePortGroup,
    alaQoSAppliedConditionSourcePortGroupStatus,
    alaQoSAppliedConditionDestinationSlot,
    alaQoSAppliedConditionDestinationSlotStatus,
    alaQoSAppliedConditionDestinationPort,
    alaQoSAppliedConditionDestinationPortGroup,
    alaQoSAppliedConditionDestinationPortGroupStatus,
    alaQoSAppliedConditionSourceMacAddr,
    alaQoSAppliedConditionSourceMacAddrStatus,
    alaQoSAppliedConditionSourceMacMask,
    alaQoSAppliedConditionSourceMacGroup,
    alaQoSAppliedConditionSourceMacGroupStatus,
    alaQoSAppliedConditionDestinationMacAddr,
    alaQoSAppliedConditionDestinationMacAddrStatus,
    alaQoSAppliedConditionDestinationMacMask,
    alaQoSAppliedConditionDestinationMacGroup,
    alaQoSAppliedConditionDestinationMacGroupStatus,
    alaQoSAppliedConditionSourceVlan,
    alaQoSAppliedConditionSourceVlanStatus,
    alaQoSAppliedConditionDestinationVlan,
    alaQoSAppliedConditionDestinationVlanStatus,
    alaQoSAppliedCondition8021p,
    alaQoSAppliedCondition8021pStatus,
    alaQoSAppliedConditionSourceIpAddr,
    alaQoSAppliedConditionSourceIpAddrStatus,
    alaQoSAppliedConditionSourceIpMask,
    alaQoSAppliedConditionSourceNetworkGroup,
    alaQoSAppliedConditionSourceNetworkGroupStatus,
    alaQoSAppliedConditionDestinationIpAddr,
    alaQoSAppliedConditionDestinationIpAddrStatus,
    alaQoSAppliedConditionDestinationIpMask,
    alaQoSAppliedConditionDestinationNetworkGroup,
    alaQoSAppliedConditionDestinationNetworkGroupStatus,
    alaQoSAppliedConditionMulticastIpAddr,
    alaQoSAppliedConditionMulticastIpAddrStatus,
    alaQoSAppliedConditionMulticastIpMask,
    alaQoSAppliedConditionMulticastNetworkGroup,
    alaQoSAppliedConditionMulticastNetworkGroupStatus,
    alaQoSAppliedConditionTos,
    alaQoSAppliedConditionTosStatus,
    alaQoSAppliedConditionTosMask,
    alaQoSAppliedConditionDscp,
    alaQoSAppliedConditionDscpStatus,
    alaQoSAppliedConditionDscpMask,
    alaQoSAppliedConditionIpProtocol,
    alaQoSAppliedConditionIpProtocolStatus,
    alaQoSAppliedConditionSourceIpPort,
    alaQoSAppliedConditionSourceIpPortStatus,
    alaQoSAppliedConditionDestinationIpPort,
    alaQoSAppliedConditionDestinationIpPortStatus,
    alaQoSAppliedConditionService,
    alaQoSAppliedConditionServiceStatus,
    alaQoSAppliedConditionServiceGroup,
    alaQoSAppliedConditionServiceGroupStatus,
    alaQoSAppliedConditionIcmpType,
    alaQoSAppliedConditionIcmpTypeStatus,
    alaQoSAppliedConditionIcmpCode,
    alaQoSAppliedConditionIcmpCodeStatus,
    alaQoSAppliedConditionRowStatus,
    alaQoSAppliedConditionSourcePortEnd,
    alaQoSAppliedConditionDestinationPortEnd,
    alaQoSAppliedConditionSourceIpPortEnd,
    alaQoSAppliedConditionDestinationIpPortEnd,
    alaQoSAppliedConditionSourceTcpPort,
    alaQoSAppliedConditionSourceTcpPortStatus,
    alaQoSAppliedConditionSourceTcpPortEnd,
    alaQoSAppliedConditionDestinationTcpPort,
    alaQoSAppliedConditionDestinationTcpPortStatus,
    alaQoSAppliedConditionDestinationTcpPortEnd,
    alaQoSAppliedConditionSourceUdpPort,
    alaQoSAppliedConditionSourceUdpPortStatus,
    alaQoSAppliedConditionSourceUdpPortEnd,
    alaQoSAppliedConditionDestinationUdpPort,
    alaQoSAppliedConditionDestinationUdpPortStatus,
    alaQoSAppliedConditionDestinationUdpPortEnd,
    alaQoSAppliedConditionEthertype,
    alaQoSAppliedConditionEthertypeStatus,
    alaQoSAppliedConditionTcpFlags,
    alaQoSAppliedConditionTcpFlagsStatus,
    alaQoSAppliedConditionTcpFlagsVal,
    alaQoSAppliedConditionTcpFlagsValStatus,
    alaQoSAppliedConditionTcpFlagsMask,
    alaQoSAppliedConditionTcpFlagsMaskStatus,
    alaQoSAppliedConditionTcpEstablished,
    alaQoSAppliedConditionSourceIpv6Addr,
    alaQoSAppliedConditionSourceIpv6AddrStatus,
    alaQoSAppliedConditionSourceIpv6Mask,
    alaQoSAppliedConditionDestinationIpv6Addr,
    alaQoSAppliedConditionDestinationIpv6AddrStatus,
    alaQoSAppliedConditionDestinationIpv6Mask,
    alaQoSAppliedConditionIpv6Traffic,
    alaQoSAppliedConditionIpv6NH,
    alaQoSAppliedConditionIpv6NHStatus,
    alaQoSAppliedConditionIpv6FlowLabel,
    alaQoSAppliedConditionIpv6FlowLabelStatus,
    alaQoSAppliedConditionMcastIpv6Addr,
    alaQoSAppliedConditionMcastIpv6AddrStatus,
    alaQoSAppliedConditionMcastIpv6Mask,
    alaQoSAppliedConditionDscpEnd,
    alaQoSAppliedConditionInnerSourceVlan,
    alaQoSAppliedConditionInnerSourceVlanStatus,
    alaQoSAppliedConditionInner8021p,
    alaQoSAppliedConditionInner8021pStatus,
    alaQoSAppliedConditionVrfName,
    alaQoSAppliedConditionVrfNameStatus,
    alaQoSAppliedConditionFragments
  }
  STATUS      current
  DESCRIPTION "Collections of objects providing information
               for applied Conditions"
  ::= { alaQoSMIBGroups 4 }

alaQoSMIBServiceObjects OBJECT-GROUP
  OBJECTS {
    alaQoSServiceSource,
    alaQoSServiceProtocol,
    alaQoSServiceSourceIpPort,
    alaQoSServiceSourceIpPortStatus,
    alaQoSServiceDestinationIpPort,
    alaQoSServiceDestinationIpPortStatus,
    alaQoSServiceRowStatus,
    alaQoSServiceSourceIpPortEnd,
    alaQoSServiceDestinationIpPortEnd,
    alaQoSServiceSourceTcpPort,
    alaQoSServiceSourceTcpPortStatus,
    alaQoSServiceSourceTcpPortEnd,
    alaQoSServiceDestinationTcpPort,
    alaQoSServiceDestinationTcpPortStatus,
    alaQoSServiceDestinationTcpPortEnd,
    alaQoSServiceSourceUdpPort,
    alaQoSServiceSourceUdpPortStatus,
    alaQoSServiceSourceUdpPortEnd,
    alaQoSServiceDestinationUdpPort,
    alaQoSServiceDestinationUdpPortStatus,
    alaQoSServiceDestinationUdpPortEnd
  }
  STATUS      current
  DESCRIPTION "Collections of objects providing information for Services"
  ::= { alaQoSMIBGroups 5 }

alaQoSMIBAppliedServiceObjects OBJECT-GROUP
  OBJECTS {
    alaQoSAppliedServiceSource,
    alaQoSAppliedServiceProtocol,
    alaQoSAppliedServiceSourceIpPort,
    alaQoSAppliedServiceSourceIpPortStatus,
    alaQoSAppliedServiceDestinationIpPort,
    alaQoSAppliedServiceDestinationIpPortStatus,
    alaQoSAppliedServiceRowStatus,
    alaQoSAppliedServiceSourceIpPortEnd,
    alaQoSAppliedServiceDestinationIpPortEnd,
    alaQoSAppliedServiceSourceTcpPort,
    alaQoSAppliedServiceSourceTcpPortStatus,
    alaQoSAppliedServiceSourceTcpPortEnd,
    alaQoSAppliedServiceDestinationTcpPort,
    alaQoSAppliedServiceDestinationTcpPortStatus,
    alaQoSAppliedServiceDestinationTcpPortEnd,
    alaQoSAppliedServiceSourceUdpPort,
    alaQoSAppliedServiceSourceUdpPortStatus,
    alaQoSAppliedServiceSourceUdpPortEnd,
    alaQoSAppliedServiceDestinationUdpPort,
    alaQoSAppliedServiceDestinationUdpPortStatus,
    alaQoSAppliedServiceDestinationUdpPortEnd
  }
  STATUS      current
  DESCRIPTION "Collections of objects providing information
               for applied Services"
  ::= { alaQoSMIBGroups 6 }

alaQoSMIBServiceGroupsObjects OBJECT-GROUP
  OBJECTS {
    alaQoSServiceGroupsSource,
    alaQoSServiceGroupsStatus
  }
  STATUS      current
  DESCRIPTION "Collections of objects providing information for ServiceGroupss"
  ::= { alaQoSMIBGroups 7 }

alaQoSMIBAppliedServiceGroupsObjects OBJECT-GROUP
  OBJECTS {
    alaQoSAppliedServiceGroupsSource,
    alaQoSAppliedServiceGroupsStatus
  }
  STATUS      current
  DESCRIPTION "Collections of objects providing information
               for applied ServiceGroupss"
  ::= { alaQoSMIBGroups 8 }

alaQoSMIBServiceGroupObjects OBJECT-GROUP
  OBJECTS {
    alaQoSServiceGroupStatus
  }
  STATUS      current
  DESCRIPTION "Collections of objects providing information for ServiceGroups"
  ::= { alaQoSMIBGroups 9 }

alaQoSMIBAppliedServiceGroupObjects OBJECT-GROUP
  OBJECTS {
    alaQoSAppliedServiceGroupStatus
  }
  STATUS      current
  DESCRIPTION "Collections of objects providing information
               for applied ServiceGroups"
  ::= { alaQoSMIBGroups 10 }

alaQoSMIBNetworkGroupsObjects OBJECT-GROUP
  OBJECTS {
    alaQoSNetworkGroupsSource,
    alaQoSNetworkGroupsStatus
  }
  STATUS      current
  DESCRIPTION "Collections of objects providing information for NetworkGroupss"
  ::= { alaQoSMIBGroups 11 }

alaQoSMIBAppliedNetworkGroupsObjects OBJECT-GROUP
  OBJECTS {
    alaQoSAppliedNetworkGroupsSource,
    alaQoSAppliedNetworkGroupsStatus
  }
  STATUS      current
  DESCRIPTION "Collections of objects providing information
               for applied NetworkGroupss"
  ::= { alaQoSMIBGroups 12 }

alaQoSMIBNetworkGroupObjects OBJECT-GROUP
  OBJECTS {
    alaQoSNetworkGroupStatus
  }
  STATUS      current
  DESCRIPTION "Collections of objects providing information for NetworkGroups"
  ::= { alaQoSMIBGroups 13 }

alaQoSMIBAppliedNetworkGroupObjects OBJECT-GROUP
  OBJECTS {
    alaQoSAppliedNetworkGroupStatus
  }
  STATUS      current
  DESCRIPTION "Collections of objects providing information
               for applied NetworkGroups"
  ::= { alaQoSMIBGroups 14 }

alaQoSMIBMACGroupsObjects OBJECT-GROUP
  OBJECTS {
    alaQoSMACGroupsSource,
    alaQoSMACGroupsStatus
  }
  STATUS      current
  DESCRIPTION "Collections of objects providing information for MACGroupss"
  ::= { alaQoSMIBGroups 15 }

alaQoSMIBAppliedMACGroupsObjects OBJECT-GROUP
  OBJECTS {
    alaQoSAppliedMACGroupsSource,
    alaQoSAppliedMACGroupsStatus
  }
  STATUS      current
  DESCRIPTION "Collections of objects providing information
               for applied MACGroupss"
  ::= { alaQoSMIBGroups 16 }

alaQoSMIBMACGroupObjects OBJECT-GROUP
  OBJECTS {
    alaQoSMACGroupStatus
  }
  STATUS      current
  DESCRIPTION "Collections of objects providing information for MACGroups"
  ::= { alaQoSMIBGroups 17 }

alaQoSMIBAppliedMACGroupObjects OBJECT-GROUP
  OBJECTS {
    alaQoSAppliedMACGroupStatus
  }
  STATUS      current
  DESCRIPTION "Collections of objects providing information
               for applied MACGroups"
  ::= { alaQoSMIBGroups 18 }

alaQoSMIBPortGroupsObjects OBJECT-GROUP
  OBJECTS {
    alaQoSPortGroupsSource,
    alaQoSPortGroupsStatus
  }
  STATUS      current
  DESCRIPTION "Collections of objects providing information for PortGroupss"
  ::= { alaQoSMIBGroups 19 }

alaQoSMIBAppliedPortGroupsObjects OBJECT-GROUP
  OBJECTS {
    alaQoSAppliedPortGroupsSource,
    alaQoSAppliedPortGroupsStatus
  }
  STATUS      current
  DESCRIPTION "Collections of objects providing information
               for applied PortGroupss"
  ::= { alaQoSMIBGroups 20 }

alaQoSMIBPortGroupObjects OBJECT-GROUP
  OBJECTS {
    alaQoSPortGroupStatus
  }
  STATUS      current
  DESCRIPTION "Collections of objects providing information for PortGroups"
  ::= { alaQoSMIBGroups 21 }

alaQoSMIBAppliedPortGroupObjects OBJECT-GROUP
  OBJECTS {
    alaQoSAppliedPortGroupStatus
  }
  STATUS      current
  DESCRIPTION "Collections of objects providing information
               for applied PortGroups"
  ::= { alaQoSMIBGroups 22 }

alaQoSMIBMapGroupsObjects OBJECT-GROUP
  OBJECTS {
    alaQoSMapGroupsSource,
    alaQoSMapGroupsStatus
  }
  STATUS      current
  DESCRIPTION "Collections of objects providing information for MapGroupss"
  ::= { alaQoSMIBGroups 23 }

alaQoSMIBAppliedMapGroupsObjects OBJECT-GROUP
  OBJECTS {
    alaQoSAppliedMapGroupsSource,
    alaQoSAppliedMapGroupsStatus
  }
  STATUS      current
  DESCRIPTION "Collections of objects providing information
               for applied MapGroupss"
  ::= { alaQoSMIBGroups 24 }

alaQoSMIBMapGroupObjects OBJECT-GROUP
  OBJECTS {
    alaQoSMapGroupStatus
  }
  STATUS      current
  DESCRIPTION "Collections of objects providing information for MapGroups"
  ::= { alaQoSMIBGroups 25 }

alaQoSMIBAppliedMapGroupObjects OBJECT-GROUP
  OBJECTS {
    alaQoSAppliedMapGroupStatus
  }
  STATUS      current
  DESCRIPTION "Collections of objects providing information
               for applied MapGroups"
  ::= { alaQoSMIBGroups 26 }

alaQoSMIBActionObjects OBJECT-GROUP
  OBJECTS {
    alaQoSActionSource,
    alaQoSActionDisposition,
    alaQoSActionMaximumBandwidth,
    alaQoSActionMaximumBandwidthStatus,
    alaQoSActionPriority,
    alaQoSActionPriorityStatus,
    alaQoSActionShared,
    alaQoSActionMaximumDepth,
    alaQoSActionMaximumDepthStatus,
    alaQoSAction8021p,
    alaQoSAction8021pStatus,
    alaQoSActionTos,
    alaQoSActionTosStatus,
    alaQoSActionDscp,
    alaQoSActionDscpStatus,
    alaQoSActionMapFrom,
    alaQoSActionMapTo,
    alaQoSActionMapGroup,
    alaQoSActionMapGroupStatus,
    alaQoSActionLoadBalanceGroup,
    alaQoSActionLoadBalanceGroupStatus,
    alaQoSActionPermanentGatewayIpAddr,
    alaQoSActionPermanentGatewayIpAddrStatus,
    alaQoSActionAlternateGatewayIpAddr,
    alaQoSActionAlternateGatewayIpAddrStatus,
    alaQoSActionRowStatus,
    alaQoSActionNocache,
    alaQoSActionPortdisable,
    alaQoSActionRedirectSlot,
    alaQoSActionRedirectSlotStatus,
    alaQoSActionRedirectPort,
    alaQoSActionRedirectAgg,
    alaQoSActionRedirectAggStatus,
    alaQoSActionMirrorSlot,
    alaQoSActionMirrorPort,
    alaQoSActionMirrorMode,
    alaQoSActionMirrorModeStatus,
    alaQoSActionCIR,
    alaQoSActionCIRStatus,
    alaQoSActionCBS,
    alaQoSActionCBSStatus,
    alaQoSActionPIR,
    alaQoSActionPIRStatus,
    alaQoSActionPBS,
    alaQoSActionPBSStatus,
    alaQoSActionCPUPriority,
    alaQoSActionCPUPriorityStatus,
    alaQoSActionColorOnly
  }
  STATUS      current
  DESCRIPTION "Collections of objects providing information for Actions"
  ::= { alaQoSMIBGroups 27 }

alaQoSMIBAppliedActionObjects OBJECT-GROUP
  OBJECTS {
    alaQoSAppliedActionSource,
    alaQoSAppliedActionDisposition,
    alaQoSAppliedActionMaximumBandwidth,
    alaQoSAppliedActionMaximumBandwidthStatus,
    alaQoSAppliedActionPriority,
    alaQoSAppliedActionPriorityStatus,
    alaQoSAppliedActionShared,
    alaQoSAppliedActionMaximumDepth,
    alaQoSAppliedActionMaximumDepthStatus,
    alaQoSAppliedAction8021p,
    alaQoSAppliedAction8021pStatus,
    alaQoSAppliedActionTos,
    alaQoSAppliedActionTosStatus,
    alaQoSAppliedActionDscp,
    alaQoSAppliedActionDscpStatus,
    alaQoSAppliedActionMapFrom,
    alaQoSAppliedActionMapTo,
    alaQoSAppliedActionMapGroup,
    alaQoSAppliedActionMapGroupStatus,
    alaQoSAppliedActionLoadBalanceGroup,
    alaQoSAppliedActionLoadBalanceGroupStatus,
    alaQoSAppliedActionPermanentGatewayIpAddr,
    alaQoSAppliedActionPermanentGatewayIpAddrStatus,
    alaQoSAppliedActionAlternateGatewayIpAddr,
    alaQoSAppliedActionAlternateGatewayIpAddrStatus,
    alaQoSAppliedActionRowStatus,
    alaQoSAppliedActionNocache,
    alaQoSAppliedActionPortdisable,
    alaQoSAppliedActionRedirectSlot,
    alaQoSAppliedActionRedirectSlotStatus,
    alaQoSAppliedActionRedirectPort,
    alaQoSAppliedActionRedirectAgg,
    alaQoSAppliedActionRedirectAggStatus,
    alaQoSAppliedActionMirrorSlot,
    alaQoSAppliedActionMirrorPort,
    alaQoSAppliedActionMirrorMode,
    alaQoSAppliedActionMirrorModeStatus,
    alaQoSAppliedActionCIR,
    alaQoSAppliedActionCIRStatus,
    alaQoSAppliedActionCBS,
    alaQoSAppliedActionCBSStatus,
    alaQoSAppliedActionPIR,
    alaQoSAppliedActionPIRStatus,
    alaQoSAppliedActionPBS,
    alaQoSAppliedActionPBSStatus,
    alaQoSAppliedActionCPUPriority,
    alaQoSAppliedActionCPUPriorityStatus,
    alaQoSAppliedActionColorOnly
  }
  STATUS      current
  DESCRIPTION "Collections of objects providing information
               for applied Actions"
  ::= { alaQoSMIBGroups 28 }

alaQoSMIBPortObjects OBJECT-GROUP
  OBJECTS {
    alaQoSPortInterfaceType,
    alaQoSPortTrusted,
    alaQoSPortDefault8021p,
    alaQoSPortDefaultDSCP,
    alaQoSPortMaximumDefaultDepth,
    alaQoSPortMaximumDefaultDepthStatus,
    alaQoSPortReset,
    alaQoSPortPhysicalBandwidth,
    alaQoSPortRowStatus,
    alaQoSPortDefaultClassification,
    alaQoSPortMaximumBandwidth,
    alaQoSPortMaximumBandwidthStatus,
    alaQoSPortMaximumIngBandwidth,
    alaQoSPortMaximumIngBandwidthStatus,
    alaQoSPortDEIMarking,
    alaQoSPortDEIMapping
  }
  STATUS      current
  DESCRIPTION "Collections of objects providing information for Ports"
  ::= { alaQoSMIBGroups 29 }

alaQoSMIBConfigObjects OBJECT-GROUP
  OBJECTS {
    alaQoSConfigEnabled,
    alaQoSConfigTrustPorts,
    alaQoSConfigStatsInterval,
    alaQoSConfigLogLines,
    alaQoSConfigLogLevel,
    alaQoSConfigLogConsole,
    alaQoSConfigForwardLog,
    alaQoSConfigClearLog,
    alaQoSConfigApply,
    alaQoSConfigRevert,
    alaQoSConfigReset,
    alaQoSConfigStatsReset,
    alaQoSConfigFlush,
    alaQoSConfigDebug,
    alaQoSConfigUserportFilter,
    alaQoSConfigAppliedUserportFilter,
    alaQoSConfigUserportShutdown,
    alaQoSConfigAppliedUserportShutdown,
    alaQoSConfigAutoPhones,
    alaQoSConfigQMPage,
    alaQoSConfigQMMACGroup,
    alaQoSConfigQMPath,
    alaQoSConfigDEIMapping,
    alaQoSConfigDEIMarking
  }
  STATUS      current
  DESCRIPTION "Collections of objects providing information for Configs"
  ::= { alaQoSMIBGroups 30 }

alaQoSMIBStatsObjects OBJECT-GROUP
  OBJECTS {
    alaQoSStatsSpoofedEvents,
    alaQoSStatsNonSpoofedEvents
  }
  STATUS      current
  DESCRIPTION "Collections of objects providing information for Statss"
  ::= { alaQoSMIBGroups 31 }


alaQoSMIBRuleGroupsObjects OBJECT-GROUP
  OBJECTS {
    alaQoSRuleGroupsSource,
    alaQoSRuleGroupsType,
    alaQoSRuleGroupsEnabled,
    alaQoSRuleGroupsStatus
  }
  STATUS      current
  DESCRIPTION "Collections of objects providing information for RuleGroupss"
  ::= { alaQoSMIBGroups 32 }

alaQoSMIBAppliedRuleGroupsObjects OBJECT-GROUP
  OBJECTS {
    alaQoSAppliedRuleGroupsSource,
    alaQoSAppliedRuleGroupsType,
    alaQoSAppliedRuleGroupsEnabled,
    alaQoSAppliedRuleGroupsStatus
  }
  STATUS      current
  DESCRIPTION "Collections of objects providing information
               for applied RuleGroupss"
  ::= { alaQoSMIBGroups 33 }

alaQoSMIBRuleGroupObjects OBJECT-GROUP
  OBJECTS {
    alaQoSRuleGroupMatches,
    alaQoSRuleGroupCountType,
    alaQoSRuleGroupPacketCount,
    alaQoSRuleGroupByteCount,
    alaQoSRuleGroupStatus
  }
  STATUS      current
  DESCRIPTION "Collections of objects providing information for RuleGroups"
  ::= { alaQoSMIBGroups 34 }

alaQoSMIBAppliedRuleGroupObjects OBJECT-GROUP
  OBJECTS {
    alaQoSAppliedRuleGroupMatches,
    alaQoSAppliedRuleGroupCountType,
    alaQoSAppliedRuleGroupPacketCount,
    alaQoSAppliedRuleGroupByteCount,
    alaQoSAppliedRuleGroupStatus
  }
  STATUS      current
  DESCRIPTION "Collections of objects providing information
               for applied RuleGroups"
  ::= { alaQoSMIBGroups 35 }

alaQoSMIBValidityPeriodObjects OBJECT-GROUP
  OBJECTS {
    alaQoSValidityPeriodSource,
    alaQoSValidityPeriodDays,
    alaQoSValidityPeriodDaysStatus,
    alaQoSValidityPeriodMonths,
    alaQoSValidityPeriodMonthsStatus,
    alaQoSValidityPeriodHour,
    alaQoSValidityPeriodHourStatus,
    alaQoSValidityPeriodEndHour,
    alaQoSValidityPeriodInterval,
    alaQoSValidityPeriodIntervalStatus,
    alaQoSValidityPeriodEndInterval,
    alaQoSValidityPeriodRowStatus
  }
  STATUS      current
  DESCRIPTION "Collections of objects providing information
               for Validity Periods"
  ::= { alaQoSMIBGroups 36 }


alaQoSMIBAppliedValidityPeriodObjects OBJECT-GROUP
  OBJECTS {
    alaQoSAppliedValidityPeriodSource,
    alaQoSAppliedValidityPeriodDays,
    alaQoSAppliedValidityPeriodDaysStatus,
    alaQoSAppliedValidityPeriodMonths,
    alaQoSAppliedValidityPeriodMonthsStatus,
    alaQoSAppliedValidityPeriodHour,
    alaQoSAppliedValidityPeriodHourStatus,
    alaQoSAppliedValidityPeriodEndHour,
    alaQoSAppliedValidityPeriodInterval,
    alaQoSAppliedValidityPeriodIntervalStatus,
    alaQoSAppliedValidityPeriodEndInterval,
    alaQoSAppliedValidityPeriodRowStatus
  }
  STATUS      current
  DESCRIPTION "Collections of objects providing information
               for applied Validity Periods"
  ::= { alaQoSMIBGroups 37 }


alaQoSMIBCompliance MODULE-COMPLIANCE
  STATUS      current
  DESCRIPTION "Compliance statement for QoS."
  MODULE
  MANDATORY-GROUPS {
    alaQoSMIBRuleObjects,
    alaQoSMIBAppliedRuleObjects,
    alaQoSMIBConditionObjects,
    alaQoSMIBAppliedConditionObjects,
    alaQoSMIBServiceObjects,
    alaQoSMIBAppliedServiceObjects,
    alaQoSMIBServiceGroupsObjects,
    alaQoSMIBAppliedServiceGroupsObjects,
    alaQoSMIBServiceGroupObjects,
    alaQoSMIBAppliedServiceGroupObjects,
    alaQoSMIBNetworkGroupsObjects,
    alaQoSMIBAppliedNetworkGroupsObjects,
    alaQoSMIBNetworkGroupObjects,
    alaQoSMIBAppliedNetworkGroupObjects,
    alaQoSMIBMACGroupsObjects,
    alaQoSMIBAppliedMACGroupsObjects,
    alaQoSMIBMACGroupObjects,
    alaQoSMIBAppliedMACGroupObjects,
    alaQoSMIBPortGroupsObjects,
    alaQoSMIBAppliedPortGroupsObjects,
    alaQoSMIBPortGroupObjects,
    alaQoSMIBAppliedPortGroupObjects,
    alaQoSMIBMapGroupsObjects,
    alaQoSMIBAppliedMapGroupsObjects,
    alaQoSMIBMapGroupObjects,
    alaQoSMIBAppliedMapGroupObjects,
    alaQoSMIBActionObjects,
    alaQoSMIBAppliedActionObjects,
    alaQoSMIBPortObjects,
    alaQoSMIBConfigObjects,
    alaQoSMIBStatsObjects,
    alaQoSMIBRuleGroupsObjects,
    alaQoSMIBAppliedRuleGroupsObjects,
    alaQoSMIBRuleGroupObjects,
    alaQoSMIBAppliedRuleGroupObjects,
    alaQoSMIBValidityPeriodObjects,
    alaQoSMIBAppliedValidityPeriodObjects
  }
  ::= { alaQoSMIBCompliances 1 }

END
